--
-- ASN.1 MIB Definitions
-- Output Date: Fri Mar 05 09:45:27 2021
--

IPE-PTP-MIB DEFINITIONS ::= BEGIN

-----------------------------------------------
-- IMPORTS Definitions
-----------------------------------------------

    IMPORTS
        InterfaceIndex, InterfaceIndexOrZero
            FROM IF-MIB
        InetAddress, InetAddressType
            FROM INET-ADDRESS-MIB
        enterprises, Gauge32, Integer32, IpAddress, NOTIFICATION-TYPE,
        OBJECT-TYPE, Unsigned32
            FROM SNMPv2-SMI
        DateAndTime, DisplayString, RowStatus, TEXTUAL-CONVENTION, TruthValue
            FROM SNMPv2-TC;

-----------------------------------------------
-- Textual Convention Definitions
-----------------------------------------------

    EnableDisableValue ::= TEXTUAL-CONVENTION
        STATUS       current
        DESCRIPTION  "Enable/Disable Type"
        SYNTAX       INTEGER { invalid(0), disable(1), enable(2) }

    IpeClockIdentity ::= TEXTUAL-CONVENTION
        STATUS       current
        DESCRIPTION  
            "The clock Identity is an 8-octet array and will be presented in
            the form of a character array. The value of the IpeClockIdentity
            should be taken from the IEEE EUI-64 individual assigned numbers
            as indicated in Section 7.5.2.2.2 of [IEEE Std. 1588-2008].  The
            EUI-64 address is divided into the following fields.
            
                OUI: bytes 0-2
                Extension identifier: bytes 3-7
            
            The clock identifier can be constructed from existing EUI-48
            assignments and here is an abbreviated example extracted from
            section 7.5.2.2.2 of [IEEE Std. 1588-2008].
            
                Company EUI-48 = 0xACDE4823456716
                EUI-64 = ACDE48FFFE23456716
            
            It is important to note the IEEE Registration Authority has
            deprecated the use of MAC-48 in any new design."
        SYNTAX       OCTET STRING (SIZE(0..8))

    IpeClockIntervalBase2 ::= TEXTUAL-CONVENTION
        STATUS       current
        DESCRIPTION  
            "The interval included in message types Announce, Sync,
            Delay_Req, and Pdelay_Req as indicated in section 7.7.2.1 of
            [IEEE Std. 1588-2008].
            
            The mean time interval between successive messages shall be
            represented as the logarithm to the base 2 of this time interval
            measured in seconds on the local clock of the device sending the
            message. The values of these logarithmic attributes shall be
            selected from integers in the range -128 to 127 subject to
            further limits established in an applicable PTP profile."
        SYNTAX       Integer32 (-128..127)

    IpeClockPortState ::= TEXTUAL-CONVENTION
        STATUS       current
        DESCRIPTION  
            "This is the value of the current state of the protocol engine
            associated with this port.
            Port state      Value     Description
            -----------------------------------------------------------
            initializing      1       In this state a port initializes
                                      its data sets, hardware, and
                                      communication facilities.
            faulty            2       The fault state of the protocol.
            disabled          3       The port shall not place any
                                      messages on its communication path.
            listening         4       The port is waiting for the
                                      announceReceiptTimeout to expire or
                                      to receive an Announce message from
                                      a master.
            preMaster         5       The port shall behave in all respects
                                      as though it were in the MASTER state
                                      except that it shall not place any
                                      messages on its communication path
                                      except for Pdelay_Req, Pdelay_Resp,
                                      Pdelay_Resp_Follow_Up, signaling, or
                                      management messages.
            master            6       The port is behaving as a master
                                      port.
            passive           7       The port shall not place any
                                      messages on its communication path
                                      except for Pdelay_Req, Pdelay_Resp,
                                      Pdelay_Resp_Follow_Up, or signaling
                                      messages, or management messages
                                      that are a required response to
                                      another management message
            uncalibrated      8       The local port is preparing to
                                      synchronize to the master port.
            slave             9       The port is synchronizing to the
                                      selected master port."
        SYNTAX       INTEGER {
                         invalid(0),
                         initializing(1),
                         faulty(2),
                         disabled(3),
                         listening(4),
                         preMaster(5),
                         master(6),
                         passive(7),
                         uncalibrated(8),
                         slave(9)
                     }

    IpeClockState ::= TEXTUAL-CONVENTION
        STATUS       current
        DESCRIPTION  
            "The clock state returned by PTP engine.
            
            Clock State      Value  Description
            --------------------------------------------------------------
            Freerun state       1   Applies to a slave device that is not
                                    locked to a master. This is the initial
                                    state a slave starts out with when it
                                    is not getting any PTP packets from the
                                    master or because of some other input
                                    error (erroneous packets, etc).
            
            Holdover state      2   In this state the slave device is
                                    locked to a master but communication
                                    with the master is lost or the
                                    timestamps in the ptp packets are
                                    incorrect. But since the slave was
                                    locked to the master, it can run with
                                    the same accuracy for sometime. The
                                    slave can continue to operate in this
                                    state for some time. If communication
                                    with the master is not restored for a
                                    while, the device is moved to the
                                    FREERUN state.
            
            Acquiring state     3   The slave device is receiving packets
                                    from a master and is trying to acquire
                                    a lock.
            
            Freq_locked state   4   Slave device is locked to the Master
                                    with respect to frequency, but not phase
                                    aligned
            
            Phase_aligned state 5   Locked to the master with respect to
                                    frequency and phase.
            
            Warm_up state       6   Warming up the internal clock source.
                                    After this state, the device is moved to
                                    the FREERUN state."
        SYNTAX       INTEGER {
                         invalid(0),
                         freerun(1),
                         holdover(2),
                         acquiring(3),
                         frequencyLocked(4),
                         phaseAligned(5),
                         warmUp(6)
                     }

    IpeClockTxMode ::= TEXTUAL-CONVENTION
        STATUS       current
        DESCRIPTION  
            "Transmission mode.
            
            unicast. Using unicast commnuication channel.
            multicast. Using Multicast communication channel.
            multicast-mix. Using multicast-unicast communication channel"
        SYNTAX       INTEGER {
                         invalid(0),
                         unicast(1),
                         multicast(2),
                         multicastmix(3),
                         unknown(99)
                     }

    IpeQualityAccuracy ::= TEXTUAL-CONVENTION
        STATUS       current
        DESCRIPTION  
            "The IpeClockQuality as specified in section 5.3.7, 7.6.2.5 an
            Table 6 of [IEEE Std. 1588-2008].
            The following values are not represented in the enumerated
            values.
            
                0x01-0x1F Reserved
                0x32-0x7F Reserved
            
            It is important to note that section 7.1.1 [RFC 2578] allows for
            gaps and enumerate values to start with zero when indicated by
            the protocol."
        SYNTAX       INTEGER {
                         invalid(0),
                         reserved00(1),
                         nanoSecond25(32),
                         nanoSecond100(33),
                         nanoSecond250(34),
                         microSec1(35),
                         microSec2dot5(36),
                         microSec10(37),
                         microSec25(38),
                         microSec100(39),
                         microSec250(40),
                         milliSec1(41),
                         milliSec2dot5(42),
                         milliSec10(43),
                         milliSec25(44),
                         milliSec100(45),
                         milliSec250(46),
                         second1(47),
                         second10(48),
                         secondGreater10(49),
                         unknown(254),
                         reserved255(255)
                     }

    IpeQualityClass ::= TEXTUAL-CONVENTION
        STATUS       current
        DESCRIPTION  
            "The IpeClockQuality as specified in section 5.3.7, 7.6.2.4 and
            Table 5 of [IEEE Std. 1588-2008].
            
             Value    Description
            ----------------------------------------------------------
                   0  Reserved to enable compatibility with future
                      versions.
                 1-5  Reserved
                   6  Shall designate a clock that is synchronized
                      to a primary reference time source.  The
                      timescale distributed shall be PTP.  A
                      clockClass 6 clock shall not be a slave to
                      another clock in the domain.
                   7  Shall designate a clock that has previously
                      been designated as clockClass 6 but that has
                      lost the ability to synchronize to a primary
                      reference time source and is in holdover mode
                      and within holdover specifications. The
                      timescale distributed shall be PTP.  A
                      clockClass 7 clock shall not be a slave to
                      another clock in the domain.
                   8  Reserved.
                9-10  Reserved to enable compatibility with future
                      versions.
               11-12  Reserved.
                  13  Shall designate a clock that is synchronized
                      to an application-specific source of time.
                      The timescale distributed shall be ARB.  A
                      clockClass 13 clock shall not be a slave to
                      another clock in the domain.
                  14  Shall designate a clock that has previously
                      been designated as clockClass 13 but that
                      has lost the ability to synchronize to an
                      application-specific source of time and is
                      in holdover mode and within holdover
                      specifications. The timescale distributed
                      shall be ARB.  A clockClass 14 clock shall
                      not be a slave to another clock in the domain.
               15-51  Reserved.
                  52  Degradation alternative A for a clock of
                      clockClass 7 that is not within holdover
                      specification.  A clock of clockClass 52
                      shall not be a slave to another clock in
                      the domain.
               53-57  Reserved.
                  58  Degradation alternative A for a clock of
                      clockClass 14 that is not within holdover
                      specification. A clock of clockClass 58 shall
                      not be a slave to another clock in the domain.
               59-67  Reserved.
              68-122  For use by alternate PTP profiles.
             123-127  Reserved.
             128-132  Reserved.
             133-170  For use by alternate PTP profiles.
             171-186  Reserved.
            
                 187  Degradation alternative B for a clock of
                      clockClass 7 that is not within holdover
                      specification. A clock of clockClass 187 may
                      be a slave to another clock in the domain.
             188-192 Reserved.
                 193 Degradation alternative B for a clock of
                     clockClass 14 that is not within holdover
                     specification. A clock of clockClass 193 may
                     be a slave to another clock in the domain.
             194-215 Reserved.
             216-232 For use by alternate PTP profiles.
             233-247 Reserved.
                 248 Default. This clockClass shall be used if
                     none of the other clockClass definitions apply.
             249-250 Reserved.
                 251 Reserved for version 1 compatibility; see Clause 18.
             252-254 Reserved.
                 255 Shall be the clockClass of a slave-only clock;
                     see 9.2.2."
        SYNTAX       Unsigned32 (0..255)

    IpeVlanIndex ::= TEXTUAL-CONVENTION
        DISPLAY-HINT "d"
        STATUS       current
        DESCRIPTION  
            "VLAN ID.
            Value '4095' is reserved, and cannot set to the system."
        SYNTAX       Integer32 (1..4094)

    IpeVlanIndexOrZero ::= TEXTUAL-CONVENTION
        DISPLAY-HINT "d"
        STATUS       current
        DESCRIPTION  
            "VLAN ID.
            Value '4095' is reserved, and cannot set to the system.
            Value '0' is special value, and the definition depends on the
            object which uses this TEXTUAL-CONVENTION."
        SYNTAX       Integer32 (0..4094)

    SeverityValue ::= TEXTUAL-CONVENTION
        STATUS       current
        DESCRIPTION  "Severity (CCITT Rec. X.733)"
        SYNTAX       INTEGER {
                         cleared(1),
                         indetermine(2),
                         critical(3),
                         major(4),
                         minor(5),
                         warning(6),
                         notReport(7)
                     }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    alarmStatusGroup OBJECT IDENTIFIER
        ::= { pasoNeoIpe-common 3 }

-----------------------------------------------
-- alarmStatusGroup Definitions
-----------------------------------------------

    asPtpGroup OBJECT IDENTIFIER
        ::= { alarmStatusGroup 47 }

    asPtpClockGroup OBJECT IDENTIFIER
        ::= { asPtpGroup 1 }

    asPtpClockModeTable OBJECT-TYPE
        SYNTAX       SEQUENCE OF AsPtpClockModeEntry
        MAX-ACCESS   not-accessible
        STATUS       current
        DESCRIPTION  "This table contains the PTP Clock information."
        ::= { asPtpClockGroup 1 }

    asPtpClockModeEntry OBJECT-TYPE
        SYNTAX       AsPtpClockModeEntry
        MAX-ACCESS   not-accessible
        STATUS       current
        DESCRIPTION  ""
        INDEX        { asPtpClockModeIndex }
        ::= { asPtpClockModeTable 1 }

    AsPtpClockModeEntry ::= SEQUENCE {
        asPtpClockModeIndex           Integer32,
        asPtpClockModeNEAddress       IpAddress,
        asPtpClockProductDescription  DisplayString,
        asPtpClockRevisionData        DisplayString,
        asPtpClockRunningState        IpeClockState,
        asPtpClockQlValue             INTEGER,
        asPtpClockClockIdentity       IpeClockIdentity
    }

    asPtpClockModeIndex OBJECT-TYPE
        SYNTAX       Integer32
        MAX-ACCESS   not-accessible
        STATUS       current
        DESCRIPTION  
            "Index of this table. The table is created per PTP card.
            value range : slot number + 1 (iPASOLINK400)
                        : 1 (iPASOLINK VR series)"
        ::= { asPtpClockModeEntry 1 }

    asPtpClockModeNEAddress OBJECT-TYPE
        SYNTAX       IpAddress
        MAX-ACCESS   not-accessible
        STATUS       current
        DESCRIPTION  "reserved."
        ::= { asPtpClockModeEntry 2 }

    asPtpClockProductDescription OBJECT-TYPE
        SYNTAX       DisplayString (SIZE(0..64))
        MAX-ACCESS   read-only
        STATUS       obsolete
        DESCRIPTION  "This object specifies the Product Description."
        ::= { asPtpClockModeEntry 3 }

    asPtpClockRevisionData OBJECT-TYPE
        SYNTAX       DisplayString (SIZE(0..32))
        MAX-ACCESS   read-only
        STATUS       obsolete
        DESCRIPTION  
            "This object specifies the revisions for node hardware (HW),
            firmware (FW), and software (SW)."
        ::= { asPtpClockModeEntry 4 }

    asPtpClockRunningState OBJECT-TYPE
        SYNTAX       IpeClockState
        MAX-ACCESS   read-only
        STATUS       current
        DESCRIPTION  
            "This object specifies the Clock state returned by PTP engine"
        ::= { asPtpClockModeEntry 5 }

    asPtpClockQlValue OBJECT-TYPE
        SYNTAX       INTEGER {
                         qlPrc(1),
                         qlSsuA(2),
                         qlSsuB(3),
                         qlOriginal(4),
                         qlSec(5),
                         qlDnu(6),
                         qlInvx(7),
                         qlFailed(8),
                         notAvail(9),
                         qlPrs(20),
                         qlStu(21),
                         qlSt2(22),
                         qlTnc(23),
                         qlSt3e(24),
                         qlSt3(25),
                         qlSmc(26),
                         qlSt4(27)
                     }
        MAX-ACCESS   read-only
        STATUS       current
        DESCRIPTION  "This object specifies the PTP Clock Quality Level."
        ::= { asPtpClockModeEntry 6 }

    asPtpClockClockIdentity OBJECT-TYPE
        SYNTAX       IpeClockIdentity
        MAX-ACCESS   read-only
        STATUS       current
        DESCRIPTION  "This object specifies the clock identity."
        ::= { asPtpClockModeEntry 7 }

    asPtpParentDSTable OBJECT-TYPE
        SYNTAX       SEQUENCE OF AsPtpParentDSEntry
        MAX-ACCESS   not-accessible
        STATUS       current
        DESCRIPTION  
            "Table of information about the PTP clock Parent Datasets"
        ::= { asPtpClockGroup 4 }

    asPtpParentDSEntry OBJECT-TYPE
        SYNTAX       AsPtpParentDSEntry
        MAX-ACCESS   not-accessible
        STATUS       current
        DESCRIPTION  ""
        INDEX        { asPtpParentDSIndex }
        ::= { asPtpParentDSTable 1 }

    AsPtpParentDSEntry ::= SEQUENCE {
        asPtpParentDSIndex                   Integer32,
        asPtpParentDSNEAddress               IpAddress,
        asPtpParentDSPortIdentity            OCTET STRING,
        asPtpParentDSStatus                  TruthValue,
        asPtpParentDSOffset                  IpeClockIntervalBase2,
        asPtpParentDSClockPhChRate           Integer32,
        asPtpParentDSGMClockIdentity         IpeClockIdentity,
        asPtpParentDSGMClockPriority1        Integer32,
        asPtpParentDSGMClockPriority2        Integer32,
        asPtpParentDSGMClockQualityClass     IpeQualityClass,
        asPtpParentDSGMClockQualityAccuracy  IpeQualityAccuracy,
        asPtpParentDSGMClockQualityOffset    Unsigned32
    }

    asPtpParentDSIndex OBJECT-TYPE
        SYNTAX       Integer32
        MAX-ACCESS   not-accessible
        STATUS       current
        DESCRIPTION  
            "Index of this table. The table is created per PTP card.
            value range : slot number + 1 (iPASOLINK400)
                        : 1 (iPASOLINK VR series)"
        ::= { asPtpParentDSEntry 1 }

    asPtpParentDSNEAddress OBJECT-TYPE
        SYNTAX       IpAddress
        MAX-ACCESS   not-accessible
        STATUS       current
        DESCRIPTION  "reserved."
        ::= { asPtpParentDSEntry 2 }

    asPtpParentDSPortIdentity OBJECT-TYPE
        SYNTAX       OCTET STRING (SIZE(0..10))
        MAX-ACCESS   read-only
        STATUS       current
        DESCRIPTION  
            "This object specifies the value of portIdentity of the port on
            the master that issues the Sync messages used in synchronizing
            this clock."
        ::= { asPtpParentDSEntry 3 }

    asPtpParentDSStatus OBJECT-TYPE
        SYNTAX       TruthValue
        MAX-ACCESS   read-only
        STATUS       current
        DESCRIPTION  
            "This object specifies the Parent Dataset ParentStats value.
            
            This value indicates whether the values of ParentDSOffset and
            ParentDSClockPhChRate have been measured and are valid.
            A TRUE value shall indicate valid data."
        ::= { asPtpParentDSEntry 4 }

    asPtpParentDSOffset OBJECT-TYPE
        SYNTAX       IpeClockIntervalBase2
        MAX-ACCESS   read-only
        STATUS       obsolete
        DESCRIPTION  
            "This object specifies the Parent Dataset
            ParentOffsetScaledLogVariance value.
            
            This value is the variance of the parent clocks phase as measured
            by the local clock."
        ::= { asPtpParentDSEntry 5 }

    asPtpParentDSClockPhChRate OBJECT-TYPE
        SYNTAX       Integer32
        MAX-ACCESS   read-only
        STATUS       obsolete
        DESCRIPTION  
            "This object specifies the clock's parent dataset
            ParentClockPhaseChangeRate value.
            
            This value is an estimate of the parent clocks phase change rate
            as measured by the slave clock."
        ::= { asPtpParentDSEntry 6 }

    asPtpParentDSGMClockIdentity OBJECT-TYPE
        SYNTAX       IpeClockIdentity
        MAX-ACCESS   read-only
        STATUS       current
        DESCRIPTION  
            "This object specifies the parent dataset Grandmaster clock
            identity."
        ::= { asPtpParentDSEntry 7 }

    asPtpParentDSGMClockPriority1 OBJECT-TYPE
        SYNTAX       Integer32 (0..255)
        MAX-ACCESS   read-only
        STATUS       current
        DESCRIPTION  
            "This object specifies the parent dataset Grandmaster clock
            priority1."
        ::= { asPtpParentDSEntry 8 }

    asPtpParentDSGMClockPriority2 OBJECT-TYPE
        SYNTAX       Integer32 (0..255)
        MAX-ACCESS   read-only
        STATUS       current
        DESCRIPTION  
            "This object specifies the parent dataset grandmaster clock
            priority2."
        ::= { asPtpParentDSEntry 9 }

    asPtpParentDSGMClockQualityClass OBJECT-TYPE
        SYNTAX       IpeQualityClass
        MAX-ACCESS   read-only
        STATUS       current
        DESCRIPTION  
            "This object specifies the parent dataset grandmaster clock
            quality class."
        ::= { asPtpParentDSEntry 10 }

    asPtpParentDSGMClockQualityAccuracy OBJECT-TYPE
        SYNTAX       IpeQualityAccuracy
        MAX-ACCESS   read-only
        STATUS       current
        DESCRIPTION  
            "This object specifies the parent dataset grandmaster clock
            quality accuracy."
        ::= { asPtpParentDSEntry 11 }

    asPtpParentDSGMClockQualityOffset OBJECT-TYPE
        SYNTAX       Unsigned32
        MAX-ACCESS   read-only
        STATUS       obsolete
        DESCRIPTION  
            "This object specifies the parent dataset grandmaster clock
            quality offset."
        ::= { asPtpParentDSEntry 12 }

    asPtpPortCurrentTable OBJECT-TYPE
        SYNTAX       SEQUENCE OF AsPtpPortCurrentEntry
        MAX-ACCESS   not-accessible
        STATUS       current
        DESCRIPTION  
            "Table of information about the clock ports running dataset."
        ::= { asPtpClockGroup 7 }

    asPtpPortCurrentEntry OBJECT-TYPE
        SYNTAX       AsPtpPortCurrentEntry
        MAX-ACCESS   not-accessible
        STATUS       current
        DESCRIPTION  ""
        INDEX        { asPtpPortCurrentIfIndex, asPtpPortCurrentIfNumber }
        ::= { asPtpPortCurrentTable 1 }

    AsPtpPortCurrentEntry ::= SEQUENCE {
        asPtpPortCurrentIfIndex          InterfaceIndex,
        asPtpPortCurrentIfNumber         Integer32,
        asPtpPortCurrentNEAddress        IpAddress,
        asPtpPortCurrentRole             INTEGER,
        asPtpPortCurrentState            IpeClockPortState,
        asPtpPortCurrentSyncOneStep      TruthValue,
        asPtpPortCurrentIpVersion        Integer32,
        asPtpPortCurrentEncapType        Integer32,
        asPtpPortCurrentTxMode           IpeClockTxMode,
        asPtpPortCurrentRxMode           IpeClockTxMode,
        asPtpPortCurrentPeerAddressType  InetAddressType,
        asPtpPortCurrentPeerAddress      InetAddress,
        asPtpPortCurrentNumOfAssocPorts  Gauge32
    }

    asPtpPortCurrentIfIndex OBJECT-TYPE
        SYNTAX       InterfaceIndex
        MAX-ACCESS   not-accessible
        STATUS       current
        DESCRIPTION  "InterfaceIndex of this table."
        ::= { asPtpPortCurrentEntry 1 }

    asPtpPortCurrentIfNumber OBJECT-TYPE
        SYNTAX       Integer32 (1..32)
        MAX-ACCESS   not-accessible
        STATUS       current
        DESCRIPTION  "Administrative Number of logical port."
        ::= { asPtpPortCurrentEntry 2 }

    asPtpPortCurrentNEAddress OBJECT-TYPE
        SYNTAX       IpAddress
        MAX-ACCESS   not-accessible
        STATUS       current
        DESCRIPTION  "reserved."
        ::= { asPtpPortCurrentEntry 3 }

    asPtpPortCurrentRole OBJECT-TYPE
        SYNTAX       INTEGER { invalid(0), master(1), slave(2) }
        MAX-ACCESS   read-only
        STATUS       obsolete
        DESCRIPTION  "This object specifies the Clock Role."
        ::= { asPtpPortCurrentEntry 4 }

    asPtpPortCurrentState OBJECT-TYPE
        SYNTAX       IpeClockPortState
        MAX-ACCESS   read-only
        STATUS       current
        DESCRIPTION  
            "This object specifies the port state returned by PTP engine."
        ::= { asPtpPortCurrentEntry 5 }

    asPtpPortCurrentSyncOneStep OBJECT-TYPE
        SYNTAX       TruthValue
        MAX-ACCESS   read-only
        STATUS       obsolete
        DESCRIPTION  
            "This object specifies that one-step clock operation between the
            PTP master and slave device is enabled."
        ::= { asPtpPortCurrentEntry 6 }

    asPtpPortCurrentIpVersion OBJECT-TYPE
        SYNTAX       Integer32
        MAX-ACCESS   read-only
        STATUS       obsolete
        DESCRIPTION  
            "This object specifirst the IP version being used for PTP
            communication (the mapping used)."
        ::= { asPtpPortCurrentEntry 7 }

    asPtpPortCurrentEncapType OBJECT-TYPE
        SYNTAX       Integer32
        MAX-ACCESS   read-only
        STATUS       obsolete
        DESCRIPTION  
            "This object specifies the type of encapsulation if the interface
            is adding extra layers (eg. VLAN, Pseudowire encapsulation...)
            for the PTP messages."
        ::= { asPtpPortCurrentEntry 8 }

    asPtpPortCurrentTxMode OBJECT-TYPE
        SYNTAX       IpeClockTxMode
        MAX-ACCESS   read-only
        STATUS       obsolete
        DESCRIPTION  
            "This object specifies the clock transmission mode as
            
            unicast:       Using unicast commnuication channel.
            multicast:     Using Multicast communication channel.
            multicast-mix: Using multicast-unicast communication channel"
        ::= { asPtpPortCurrentEntry 9 }

    asPtpPortCurrentRxMode OBJECT-TYPE
        SYNTAX       IpeClockTxMode
        MAX-ACCESS   read-only
        STATUS       obsolete
        DESCRIPTION  
            "This object specifies the clock transmission mode as
            
            unicast:       Using unicast commnuication channel.
            multicast:     Using Multicast communication channel.
            multicast-mix: Using multicast-unicast communication channel"
        ::= { asPtpPortCurrentEntry 10 }

    asPtpPortCurrentPeerAddressType OBJECT-TYPE
        SYNTAX       InetAddressType
        MAX-ACCESS   read-only
        STATUS       obsolete
        DESCRIPTION  
            "This object specifies the current peer's network address used
            for PTP communication. Based on the scenario and the setup
            involved, the values might look like these -
            Scenario                   Value
            -------------------   ----------------
            Single Master          master port
            Multiple Masters       selected master port
            Single Slave           slave port
            Multiple Slaves        <empty>
            
            (In relevant setups, information on available slaves and
            available masters will be available through
            asPtpPortAssociateTable)"
        ::= { asPtpPortCurrentEntry 11 }

    asPtpPortCurrentPeerAddress OBJECT-TYPE
        SYNTAX       InetAddress
        MAX-ACCESS   read-only
        STATUS       obsolete
        DESCRIPTION  
            "This object specifies the current peer's network address used
            for PTP communication. Based on the scenario and the setup
            involved, the values might look like these -
            Scenario                   Value
            -------------------   ----------------
            Single Master          master port
            Multiple Masters       selected master port
            Single Slave           slave port
            Multiple Slaves        <empty>
            
            (In relevant setups, information on available slaves and
            available masters will be available through
            asPtpPortAssociateTable)"
        ::= { asPtpPortCurrentEntry 12 }

    asPtpPortCurrentNumOfAssocPorts OBJECT-TYPE
        SYNTAX       Gauge32
        MAX-ACCESS   read-only
        STATUS       obsolete
        DESCRIPTION  
            "This object specifies -
            For a master port - the number of PTP slave sessions (peers)
            associated with this PTP port.
            For a slave port - the number of masters available to this slave
            port (might or might not be peered)."
        ::= { asPtpPortCurrentEntry 13 }

    asPtpUnicastMasterTable OBJECT-TYPE
        SYNTAX       SEQUENCE OF AsPtpUnicastMasterEntry
        MAX-ACCESS   not-accessible
        STATUS       current
        DESCRIPTION  
            "This table contains unicast master node information and are
            created when the unicast master is registered."
        ::= { asPtpClockGroup 9 }

    asPtpUnicastMasterEntry OBJECT-TYPE
        SYNTAX       AsPtpUnicastMasterEntry
        MAX-ACCESS   not-accessible
        STATUS       current
        DESCRIPTION  ""
        INDEX        { asPtpUnicastMasterCardIndex, asPtpUnicastMasterIndex }
        ::= { asPtpUnicastMasterTable 1 }

    AsPtpUnicastMasterEntry ::= SEQUENCE {
        asPtpUnicastMasterCardIndex          Integer32,
        asPtpUnicastMasterIndex              Integer32,
        asPtpUnicastMasterNEAddress          IpAddress,
        asPtpUnicastMasterClockId            IpeClockIdentity,
        asPtpUnicastMasterInetAddressType    InetAddressType,
        asPtpUnicastMasterInetAddress        InetAddress,
        asPtpUnicastMasterClockClass         IpeQualityClass,
        asPtpUnicastMasterStatus             INTEGER,
        asPtpUnicastMasterLossAnnounceAlarm  SeverityValue,
        asPtpUnicastMasterLossSyncAlarm      SeverityValue,
        asPtpUnicastMasterUnusableAlarm      SeverityValue,
        asPtpUnicastMasterAssociatedIfIndex  InterfaceIndexOrZero,
        asPtpUnicastMasterAssociatedIfNum    Integer32
    }

    asPtpUnicastMasterCardIndex OBJECT-TYPE
        SYNTAX       Integer32
        MAX-ACCESS   not-accessible
        STATUS       current
        DESCRIPTION  
            "Index of this table. The value is equivalent to slot id.
            value range : slot number + 1 (iPASOLINK400)
                        : 1 (iPASOLINK VR series)"
        ::= { asPtpUnicastMasterEntry 1 }

    asPtpUnicastMasterIndex OBJECT-TYPE
        SYNTAX       Integer32 (1..5)
        MAX-ACCESS   not-accessible
        STATUS       current
        DESCRIPTION  "This objects specifies the unicast master index."
        ::= { asPtpUnicastMasterEntry 2 }

    asPtpUnicastMasterNEAddress OBJECT-TYPE
        SYNTAX       IpAddress
        MAX-ACCESS   not-accessible
        STATUS       current
        DESCRIPTION  "reserved."
        ::= { asPtpUnicastMasterEntry 3 }

    asPtpUnicastMasterClockId OBJECT-TYPE
        SYNTAX       IpeClockIdentity
        MAX-ACCESS   read-only
        STATUS       current
        DESCRIPTION  "Clock Identity of Unicast Master Node."
        ::= { asPtpUnicastMasterEntry 4 }

    asPtpUnicastMasterInetAddressType OBJECT-TYPE
        SYNTAX       InetAddressType
        MAX-ACCESS   read-only
        STATUS       obsolete
        DESCRIPTION  "Address Type of Unicast Master Node."
        ::= { asPtpUnicastMasterEntry 5 }

    asPtpUnicastMasterInetAddress OBJECT-TYPE
        SYNTAX       InetAddress
        MAX-ACCESS   read-only
        STATUS       obsolete
        DESCRIPTION  "IP Address of Unicast Master Node."
        ::= { asPtpUnicastMasterEntry 6 }

    asPtpUnicastMasterClockClass OBJECT-TYPE
        SYNTAX       IpeQualityClass
        MAX-ACCESS   read-only
        STATUS       current
        DESCRIPTION  "The Clock Quality Class of the Unicast Master node."
        ::= { asPtpUnicastMasterEntry 7 }

    asPtpUnicastMasterStatus OBJECT-TYPE
        SYNTAX       INTEGER {
                         invalid(0),
                         notSelected(1),
                         selected(2),
                         forced(3)
                     }
        MAX-ACCESS   read-only
        STATUS       current
        DESCRIPTION  
            "The object specifies the selection status of unicast master as
            
            notSelected:master entry is not selected
            selected:   master entry is selected
            forced:     master entry is selected by force switch control
            waitToRestore: master entry is under wait to restore
            
            
            for example, if the master3 is selected by normal selection
            algorithm, the value of this object will shown below.
              asPtpUnicastMasterState.1,2,4,5 = notSelected
              asPtpUnicastMasterState.3 = selected
            and other example, if the master5 is selected by the forced
            switch control,
              asPtpUnicastMasterState.1,2,3,4 = notSelected
              asPtpUnicastMasterState.5 = forced"
        ::= { asPtpUnicastMasterEntry 8 }

    asPtpUnicastMasterLossAnnounceAlarm OBJECT-TYPE
        SYNTAX       SeverityValue
        MAX-ACCESS   read-only
        STATUS       current
        DESCRIPTION  
            "This object specifies whether the PTSF Loss Announce Alarm is
            detected for the unicast master."
        ::= { asPtpUnicastMasterEntry 9 }

    asPtpUnicastMasterLossSyncAlarm OBJECT-TYPE
        SYNTAX       SeverityValue
        MAX-ACCESS   read-only
        STATUS       current
        DESCRIPTION  
            "This object specifies whether the PTSF Loss Sync Alarm is
            detected for the unicast master."
        ::= { asPtpUnicastMasterEntry 10 }

    asPtpUnicastMasterUnusableAlarm OBJECT-TYPE
        SYNTAX       SeverityValue
        MAX-ACCESS   read-only
        STATUS       current
        DESCRIPTION  
            "This object specifies whether the PTSF Unusable Alarm is
            detected for the unicast master."
        ::= { asPtpUnicastMasterEntry 11 }

    asPtpUnicastMasterAssociatedIfIndex OBJECT-TYPE
        SYNTAX       InterfaceIndexOrZero
        MAX-ACCESS   read-only
        STATUS       obsolete
        DESCRIPTION  
            "this object specifies the interface which is associated by the
            unicast master."
        ::= { asPtpUnicastMasterEntry 12 }

    asPtpUnicastMasterAssociatedIfNum OBJECT-TYPE
        SYNTAX       Integer32 (0..5)
        MAX-ACCESS   read-only
        STATUS       obsolete
        DESCRIPTION  
            "this object specifies the logical interface number which is
            associated by the unicast master."
        ::= { asPtpUnicastMasterEntry 13 }

    asPtpMulticastMasterTable OBJECT-TYPE
        SYNTAX       SEQUENCE OF AsPtpMulticastMasterEntry
        MAX-ACCESS   not-accessible
        STATUS       current
        DESCRIPTION  
            "This table contains multicast master node information.
            This table is created automatically when
            provPtpClockUnicastCapability is 'disable' and the logical
            interface is created."
        ::= { asPtpClockGroup 10 }

    asPtpMulticastMasterEntry OBJECT-TYPE
        SYNTAX       AsPtpMulticastMasterEntry
        MAX-ACCESS   not-accessible
        STATUS       current
        DESCRIPTION  ""
        INDEX        { asPtpMulticastMasterIfIndex, asPtpMulticastMasterIfNum }
        ::= { asPtpMulticastMasterTable 1 }

    AsPtpMulticastMasterEntry ::= SEQUENCE {
        asPtpMulticastMasterIfIndex            InterfaceIndex,
        asPtpMulticastMasterIfNum              Integer32,
        asPtpMulticastMasterNEAddress          IpAddress,
        asPtpMulticastMasterClockId            IpeClockIdentity,
        asPtpMulticastMasterInetAddressType    InetAddressType,
        asPtpMulticastMasterInetAddress        InetAddress,
        asPtpMulticastMasterClockClass         IpeQualityClass,
        asPtpMulticastMasterStatus             INTEGER,
        asPtpMulticastMasterLossAnnounceAlarm  SeverityValue,
        asPtpMulticastMasterLossSyncAlarm      SeverityValue,
        asPtpMulticastMasterUnusableAlarm      SeverityValue
    }

    asPtpMulticastMasterIfIndex OBJECT-TYPE
        SYNTAX       InterfaceIndex
        MAX-ACCESS   not-accessible
        STATUS       current
        DESCRIPTION  
            "Index of this table. This object represents the interface which
            is associated by the multicast master node."
        ::= { asPtpMulticastMasterEntry 1 }

    asPtpMulticastMasterIfNum OBJECT-TYPE
        SYNTAX       Integer32 (1..32)
        MAX-ACCESS   not-accessible
        STATUS       current
        DESCRIPTION  
            "Index of this table. This object represents the locagical
            interface number which is associated by the multicast master
            node.
            range : 1 - 5 (iPASOLINK400), 1 - 32 (iPASOLINK VR series)"
        ::= { asPtpMulticastMasterEntry 2 }

    asPtpMulticastMasterNEAddress OBJECT-TYPE
        SYNTAX       IpAddress
        MAX-ACCESS   not-accessible
        STATUS       current
        DESCRIPTION  "reserved."
        ::= { asPtpMulticastMasterEntry 3 }

    asPtpMulticastMasterClockId OBJECT-TYPE
        SYNTAX       IpeClockIdentity
        MAX-ACCESS   read-only
        STATUS       current
        DESCRIPTION  "Clock Identity of Muticast Master Node."
        ::= { asPtpMulticastMasterEntry 4 }

    asPtpMulticastMasterInetAddressType OBJECT-TYPE
        SYNTAX       InetAddressType
        MAX-ACCESS   read-only
        STATUS       current
        DESCRIPTION  "Address Type of Multicast Master Node."
        ::= { asPtpMulticastMasterEntry 5 }

    asPtpMulticastMasterInetAddress OBJECT-TYPE
        SYNTAX       InetAddress
        MAX-ACCESS   read-only
        STATUS       current
        DESCRIPTION  "IP Address of Multicast Master Node."
        ::= { asPtpMulticastMasterEntry 6 }

    asPtpMulticastMasterClockClass OBJECT-TYPE
        SYNTAX       IpeQualityClass
        MAX-ACCESS   read-only
        STATUS       current
        DESCRIPTION  
            "The Clock Quality Class of the Multicast Master node."
        ::= { asPtpMulticastMasterEntry 7 }

    asPtpMulticastMasterStatus OBJECT-TYPE
        SYNTAX       INTEGER {
                         invalid(0),
                         notSelected(1),
                         selected(2),
                         forced(3)
                     }
        MAX-ACCESS   read-only
        STATUS       current
        DESCRIPTION  
            "The object specifies the selection status of Multicast master as
            
            notSelected: node is not selected
            selected:    node is selected
            forced:      node is selected by force switch control
            
            for example, if the master3 is selected by normal selection
            algorithm, the value of this object will shown below.
              asPtpMulticastMasterState.1,2,4,5 = notSelected
              asPtpMulticastMasterState.3 = selected
            and other example, if the master5 is selected by the forced
            switch control,
              asPtpMulticastMasterState.1,2,3,4 = notSelected
              asPtpMulticastMasterState.5 = forced"
        ::= { asPtpMulticastMasterEntry 8 }

    asPtpMulticastMasterLossAnnounceAlarm OBJECT-TYPE
        SYNTAX       SeverityValue
        MAX-ACCESS   read-only
        STATUS       obsolete
        DESCRIPTION  
            "This object specifies whether the PTSF Loss Announce Alarm is
            detected for the multicast master."
        ::= { asPtpMulticastMasterEntry 9 }

    asPtpMulticastMasterLossSyncAlarm OBJECT-TYPE
        SYNTAX       SeverityValue
        MAX-ACCESS   read-only
        STATUS       obsolete
        DESCRIPTION  
            "This object specifies whether the PTSF Loss Sync Alarm is
            detected for the multicast master."
        ::= { asPtpMulticastMasterEntry 10 }

    asPtpMulticastMasterUnusableAlarm OBJECT-TYPE
        SYNTAX       SeverityValue
        MAX-ACCESS   read-only
        STATUS       obsolete
        DESCRIPTION  
            "This object specifies whether the PTSF Unusable Alarm is
            detected for the multicast master."
        ::= { asPtpMulticastMasterEntry 11 }

    asPtpSlaveTable OBJECT-TYPE
        SYNTAX       SEQUENCE OF AsPtpSlaveEntry
        MAX-ACCESS   not-accessible
        STATUS       current
        DESCRIPTION  
            "This table contains slave node information and created
            automatically when the slave node is discovered."
        ::= { asPtpClockGroup 11 }

    asPtpSlaveEntry OBJECT-TYPE
        SYNTAX       AsPtpSlaveEntry
        MAX-ACCESS   not-accessible
        STATUS       current
        DESCRIPTION  ""
        INDEX        {
                         asPtpSlaveCardIndex,
                         asPtpSlaveClockId,
                         asPtpSlaveInetAddressType,
                         asPtpSlaveInetAddress
                     }
        ::= { asPtpSlaveTable 1 }

    AsPtpSlaveEntry ::= SEQUENCE {
        asPtpSlaveCardIndex          Integer32,
        asPtpSlaveClockId            IpeClockIdentity,
        asPtpSlaveInetAddressType    InetAddressType,
        asPtpSlaveInetAddress        InetAddress,
        asPtpSlaveNEAddress          IpAddress,
        asPtpSlaveAssociatedStatus   INTEGER,
        asPtpSlaveAssociatedIfIndex  InterfaceIndex,
        asPtpSlaveAssociatedIfNum    Integer32
    }

    asPtpSlaveCardIndex OBJECT-TYPE
        SYNTAX       Integer32
        MAX-ACCESS   not-accessible
        STATUS       current
        DESCRIPTION  
            "Index of this table. This object specifies slot number of the
            card which connected to the slave node.
            value range : slot number + 1 (iPASOLINK400)
                        : 1 (iPASOLINK VR series)"
        ::= { asPtpSlaveEntry 1 }

    asPtpSlaveClockId OBJECT-TYPE
        SYNTAX       IpeClockIdentity
        MAX-ACCESS   not-accessible
        STATUS       current
        DESCRIPTION  "This object specifies Clock Identity of slave node."
        ::= { asPtpSlaveEntry 2 }

    asPtpSlaveInetAddressType OBJECT-TYPE
        SYNTAX       InetAddressType
        MAX-ACCESS   not-accessible
        STATUS       current
        DESCRIPTION  "This object specifies Address type of slave node."
        ::= { asPtpSlaveEntry 3 }

    asPtpSlaveInetAddress OBJECT-TYPE
        SYNTAX       InetAddress
        MAX-ACCESS   not-accessible
        STATUS       current
        DESCRIPTION  "This object specifies IP Address of slave node."
        ::= { asPtpSlaveEntry 4 }

    asPtpSlaveNEAddress OBJECT-TYPE
        SYNTAX       IpAddress
        MAX-ACCESS   not-accessible
        STATUS       current
        DESCRIPTION  "reserved."
        ::= { asPtpSlaveEntry 5 }

    asPtpSlaveAssociatedStatus OBJECT-TYPE
        SYNTAX       INTEGER { invalid(0), connected(1), notConnected(4) }
        MAX-ACCESS   read-only
        STATUS       current
        DESCRIPTION  
            "This object shows the associated Slave node status.
            When the new node is detected, the new instance will be created
            and the status is set to 'connected'.
            When the associated node is removed because of the timeout, the
            value will be changed to 'timeout' and the instance will be
            removed. the value 'cancelled' means that the associated node is
            remove because of disconnect request from slave node."
        ::= { asPtpSlaveEntry 6 }

    asPtpSlaveAssociatedIfIndex OBJECT-TYPE
        SYNTAX       InterfaceIndex
        MAX-ACCESS   read-only
        STATUS       obsolete
        DESCRIPTION  
            "this object specifies the interface which is associated by the
            slave node."
        ::= { asPtpSlaveEntry 7 }

    asPtpSlaveAssociatedIfNum OBJECT-TYPE
        SYNTAX       Integer32 (1..32)
        MAX-ACCESS   read-only
        STATUS       obsolete
        DESCRIPTION  
            "this object specifies the logical interface number which is
            associated by the slave node."
        ::= { asPtpSlaveEntry 8 }

    asPtpCardGroup OBJECT IDENTIFIER
        ::= { asPtpGroup 2 }

    asPtpCardTable OBJECT-TYPE
        SYNTAX       SEQUENCE OF AsPtpCardEntry
        MAX-ACCESS   not-accessible
        STATUS       current
        DESCRIPTION  
            "This table contains the alarm and status information about PTP
            card."
        ::= { asPtpCardGroup 1 }

    asPtpCardEntry OBJECT-TYPE
        SYNTAX       AsPtpCardEntry
        MAX-ACCESS   not-accessible
        STATUS       current
        DESCRIPTION  ""
        INDEX        { asPtpCardIndex }
        ::= { asPtpCardTable 1 }

    AsPtpCardEntry ::= SEQUENCE {
        asPtpCardIndex           Integer32,
        asPtpCardNEAddress       IpAddress,
        asPtpCardModuleFail      SeverityValue,
        asPtpCardComFailAlarm    SeverityValue,
        asPtpCardUnequipped      SeverityValue,
        asPtpCardTypeMismatch    SeverityValue,
        asPtpCardBusErrorTx      SeverityValue,
        asPtpCardBusErrorRx      SeverityValue,
        asPtpCardClockFail       SeverityValue,
        asPtpCardToDin           SeverityValue,
        asPtpCardPPSin           SeverityValue,
        asPtpCardToDInformation  DateAndTime
    }

    asPtpCardIndex OBJECT-TYPE
        SYNTAX       Integer32
        MAX-ACCESS   not-accessible
        STATUS       current
        DESCRIPTION  
            "Index of this table. The table is created per PTP card.
            value range : slot number + 1 (iPASOLINK400)
                        : 1 (iPASOLINK VR series)"
        ::= { asPtpCardEntry 1 }

    asPtpCardNEAddress OBJECT-TYPE
        SYNTAX       IpAddress
        MAX-ACCESS   not-accessible
        STATUS       current
        DESCRIPTION  "reserved."
        ::= { asPtpCardEntry 2 }

    asPtpCardModuleFail OBJECT-TYPE
        SYNTAX       SeverityValue
        MAX-ACCESS   read-only
        STATUS       obsolete
        DESCRIPTION  
            "MODULE Fail Alarm. The object reports the card doesn't work
            properly."
        ::= { asPtpCardEntry 3 }

    asPtpCardComFailAlarm OBJECT-TYPE
        SYNTAX       SeverityValue
        MAX-ACCESS   read-only
        STATUS       obsolete
        DESCRIPTION  
            "COMMUNICATION Fail Alarm. The object reports the failure of the
            control channel between PTP card and main card."
        ::= { asPtpCardEntry 4 }

    asPtpCardUnequipped OBJECT-TYPE
        SYNTAX       SeverityValue
        MAX-ACCESS   read-only
        STATUS       obsolete
        DESCRIPTION  
            "UNEQUIPPED Alarm. The object reports the card is not installed
            properly."
        ::= { asPtpCardEntry 5 }

    asPtpCardTypeMismatch OBJECT-TYPE
        SYNTAX       SeverityValue
        MAX-ACCESS   read-only
        STATUS       obsolete
        DESCRIPTION  
            "TYPE MISMATCH Alarm. The object reports the installed card is
            not PTP card."
        ::= { asPtpCardEntry 6 }

    asPtpCardBusErrorTx OBJECT-TYPE
        SYNTAX       SeverityValue
        MAX-ACCESS   read-only
        STATUS       obsolete
        DESCRIPTION  
            "TX BUS ERROR Alarm. The object reports the failure of the Data
            traffic channel."
        ::= { asPtpCardEntry 7 }

    asPtpCardBusErrorRx OBJECT-TYPE
        SYNTAX       SeverityValue
        MAX-ACCESS   read-only
        STATUS       obsolete
        DESCRIPTION  
            "RX BUS ERROR Alarm. The object reports the failure of the Data
            traffic channel."
        ::= { asPtpCardEntry 8 }

    asPtpCardClockFail OBJECT-TYPE
        SYNTAX       SeverityValue
        MAX-ACCESS   read-only
        STATUS       obsolete
        DESCRIPTION  
            "PTP CLK FAIL Alarm. The object reports the abnormal temperature
            around the internal clock."
        ::= { asPtpCardEntry 9 }

    asPtpCardToDin OBJECT-TYPE
        SYNTAX       SeverityValue
        MAX-ACCESS   read-only
        STATUS       obsolete
        DESCRIPTION  
            "ToD Interface Input Alarm. The object reports the input failure
            of ToD interface."
        ::= { asPtpCardEntry 10 }

    asPtpCardPPSin OBJECT-TYPE
        SYNTAX       SeverityValue
        MAX-ACCESS   read-only
        STATUS       obsolete
        DESCRIPTION  
            "PPS Interface Input Alarm. The object reports the input failure
            of PPS interface."
        ::= { asPtpCardEntry 11 }

    asPtpCardToDInformation OBJECT-TYPE
        SYNTAX       DateAndTime
        MAX-ACCESS   read-only
        STATUS       current
        DESCRIPTION  
            "the object reports the time of day information which is
            announced on the PTP network."
        ::= { asPtpCardEntry 12 }

-----------------------------------------------
-- End User MIB Object Definitions
-----------------------------------------------

END
