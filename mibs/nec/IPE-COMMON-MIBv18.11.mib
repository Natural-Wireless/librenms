--
-- ASN.1 MIB Definitions
-- Output Date: Wed Nov 16 20:33:28 2022
--

IPE-COMMON-MIB DEFINITIONS ::= BEGIN

-----------------------------------------------
-- IMPORTS Definitions
-----------------------------------------------

    IMPORTS
        BridgeId
            FROM BRIDGE-MIB
        InterfaceIndex, InterfaceIndexOrZero
            FROM IF-MIB
        Ipv6Address
            FROM IPV6-TC
        Counter32, Counter64, enterprises, Gauge32, Integer32, IpAddress,
        NOTIFICATION-TYPE, OBJECT-TYPE, Unsigned32
            FROM SNMPv2-SMI
        DateAndTime, DisplayString, MacAddress, RowStatus,
        TEXTUAL-CONVENTION, TruthValue
            FROM SNMPv2-TC;

-----------------------------------------------
-- Textual Convention Definitions
-----------------------------------------------

    AlarmTypeValue ::= TEXTUAL-CONVENTION
        STATUS       current
        DESCRIPTION  "Alarm Type (CCITT Rec. X.733)"
        SYNTAX       INTEGER {
                         invalid(0),
                         communicationsAlarm(1),
                         qualityOfServiceAlarm(2),
                         processingErrorAlarm(3),
                         equipmentAlarm(4),
                         environmentalAlarm(5),
                         integrityViolationAlarm(6),
                         operationalViolationAlarm(7),
                         physicalViolationAlarm(8),
                         securityViolationAlarm(9),
                         timeDomainViolationAlarm(10)
                     }

    EnableDisableValue ::= TEXTUAL-CONVENTION
        STATUS       current
        DESCRIPTION  "Enable/Disable Type"
        SYNTAX       INTEGER { invalid(0), disable(1), enable(2) }

    IpeMepId ::= TEXTUAL-CONVENTION
        DISPLAY-HINT "d"
        STATUS       current
        DESCRIPTION  
            "Administrative MEP ID value.
            This value is not same as MEP ID in protocol sense."
        SYNTAX       Integer32 (1..128)

    IpeStatsInfo ::= TEXTUAL-CONVENTION
        STATUS       current
        DESCRIPTION  
            "PMON/RMON monitoring status.
            'invalid' means the corresponding monitoring value is not
            reliable because of the alarm or other reasons. 'maintenance'
            means that some maintenance functions are executed on the current
            interval."
        SYNTAX       INTEGER {
                         invalid(0),
                         validNoMaint(1),
                         validMaint(2),
                         invalidNoMaint(3),
                         invalidMaint(4)
                     }

    IpeUnsigned64 ::= TEXTUAL-CONVENTION
        STATUS       current
        DESCRIPTION  
            "A 64-bit unsigned integer.  The value is
            restricted to the BER serialization of the following
            ASN.1 type:
                U64TYPE ::= [123] IMPLICIT U64Type
            (note: the value 123 is the sum of '30'h and '4b'h)
            The BER serialization of the length for values of
            this type must use the definite length, short
            encoding form.
            For example, the BER serialization of value 129
            of type U64TYPE is '9f7b020081'h.  (The tag is '9f7b'h;
            the length is '02'h; and the value is '0081'h.) The
            BER serialization of value '9f7b020081'h of data
            type Opaque is '44059f7b020081'h. (The tag is '44'h;
            the length is '05'h; and the value is '9f7b020081'h.)"
        SYNTAX       Opaque (SIZE(4..12))

    IpeVlanIndexOrZero ::= TEXTUAL-CONVENTION
        DISPLAY-HINT "d"
        STATUS       current
        DESCRIPTION  
            "VLAN ID.
            Value '4095' is reserved, and cannot set to the system.
            Value '0' is special value, and the definition depends on the
            object which uses this TEXTUAL-CONVENTION."
        SYNTAX       Integer32 (0..4094)

    IpeVlanList ::= TEXTUAL-CONVENTION
        STATUS       current
        DESCRIPTION  ""
        SYNTAX       OCTET STRING (SIZE(512..512))

    IpeVlanListOrZero ::= TEXTUAL-CONVENTION
        STATUS       current
        DESCRIPTION  
            "VLAN List.
            Each octet represents a set of eight VIDs. The first octet
            specifying VID 1 through 8, the second octet specifying VID 9
            through 16, etc.
            If that bit has a value of '1' then that VID is included in the
            set of VIDs; the VID is not included if its bit has a value of
            '0'."
        SYNTAX       OCTET STRING (SIZE(0..0|512..512))

    OffOnValue ::= TEXTUAL-CONVENTION
        STATUS       current
        DESCRIPTION  "Off/On Type"
        SYNTAX       INTEGER { invalid(0), off(1), on(2) }

    ProbableCauseValue ::= TEXTUAL-CONVENTION
        STATUS       current
        DESCRIPTION  "Probable Cause (CCITT Rec. X.733)"
        SYNTAX       INTEGER {
                         invalid(0),
                         aIS(1),
                         callSetUpFailure(2),
                         degradedSignal(3),
                         farEndReceiverFailure(4),
                         framingError(5),
                         lossOfFrame(6),
                         lossOfPointer(7),
                         lossOfSignal(8),
                         payloadTypeMismatch(9),
                         transmissionError(10),
                         remoteAlarmInterface(11),
                         excessiveBER(12),
                         pathTraceMismatch(13),
                         unavailable(14),
                         signalLabelMismatch(15),
                         lossOfMultiFrame(16),
                         receiveFailure(17),
                         transmitFailure(18),
                         modulationFailure(19),
                         demodulationFailure(20),
                         broadcastChannelFailure(21),
                         connectionEstablishmentError(22),
                         invalidMessageReceived(23),
                         localNodeTransmissionError(24),
                         remoteNodeTransmissionError(25),
                         routingFailure(26),
                         backplaneFailure(51),
                         dataSetProblem(52),
                         equipmentIdentifierDuplication(53),
                         externalIFDeviceProblem(54),
                         lineCardProblem(55),
                         multiplexerProblem(56),
                         nEIdentifierDuplication(57),
                         powerProblem(58),
                         processorProblem(59),
                         protectionPathFailure(60),
                         receiverFailure(61),
                         replaceableUnitMissing(62),
                         replaceableUnitTypeMismatch(63),
                         synchronizationSourceMismatch(64),
                         terminalProblem(65),
                         timingProblem(66),
                         transmitterFailure(67),
                         trunkCardProblem(68),
                         replaceableUnitProblem(69),
                         realTimeClockFailure(70),
                         antennaFailure(71),
                         batteryChargingFailure(72),
                         diskFailure(73),
                         frequencyHoppingFailure(74),
                         iODeviceError(75),
                         lossOfSynchronisation(76),
                         lossOfRedundancy(77),
                         powerSupplyFailure(78),
                         signalQualityEvaluationFailure(79),
                         tranceiverFailure(80),
                         protectionMechanismFailure(81),
                         protectingResourceFailure(82),
                         airCompressorFailure(101),
                         airConditioningFailure(102),
                         airDryerFailure(103),
                         batteryDischarging(104),
                         batteryFailure(105),
                         commercialPowerFailure(106),
                         coolingFanFailure(107),
                         engineFailure(108),
                         fireDetectorFailure(109),
                         fuseFailure(110),
                         generatorFailure(111),
                         lowBatteryThreshold(112),
                         pumpFailure(113),
                         rectifierFailure(114),
                         rectifierHighVoltage(115),
                         rectifierLowFVoltage(116),
                         ventilationsSystemFailure(117),
                         enclosureDoorOpen(118),
                         explosiveGas(119),
                         fire(120),
                         flood(121),
                         highHumidity(122),
                         highTemperature(123),
                         highWind(124),
                         iceBuildUp(125),
                         intrusionDetection(126),
                         lowFuel(127),
                         lowHumidity(128),
                         lowCablePressure(129),
                         lowTemperatue(130),
                         lowWater(131),
                         smoke(132),
                         toxicGas(133),
                         coolingSystemFailure(134),
                         externalEquipmentFailure(135),
                         externalPointFailure(136),
                         storageCapacityProblem(151),
                         memoryMismatch(152),
                         corruptData(153),
                         outOfCPUCycles(154),
                         sfwrEnvironmentProblem(155),
                         sfwrDownloadFailure(156),
                         lossOfRealTimel(157),
                         applicationSubsystemFailure(158),
                         configurationOrCustomisationError(159),
                         databaseInconsistency(160),
                         fileError(161),
                         outOfMemory(162),
                         softwareError(163),
                         timeoutExpired(164),
                         underlayingResourceUnavailable(165),
                         versionMismatch(166),
                         bandwidthReduced(201),
                         congestion(202),
                         excessiveErrorRate(203),
                         excessiveResponseTime(204),
                         excessiveRetransmissionRate(205),
                         reducedLoggingCapability(206),
                         systemResourcesOverload(207),
                         adapterError(500),
                         applicationSubsystemFailture(501),
                         bandwidthReducedX733(502),
                         callEstablishmentError(503),
                         communicationsProtocolError(504),
                         communicationsSubsystemFailure(505),
                         configurationOrCustomizationError(506),
                         congestionX733(507),
                         coruptData(508),
                         cpuCyclesLimitExceeded(509),
                         dataSetOrModemError(510),
                         degradedSignalX733(511),
                         dteDceInterfaceError(512),
                         enclosureDoorOpenX733(513),
                         equipmentMalfunction(514),
                         excessiveVibration(515),
                         fileErrorX733(516),
                         fireDetected(517),
                         framingErrorX733(518),
                         heatingVentCoolingSystemProblem(519),
                         humidityUnacceptable(520),
                         inputOutputDeviceError(521),
                         inputDeviceError(522),
                         lanError(523),
                         leakDetected(524),
                         localNodeTransmissionErrorX733(525),
                         lossOfFrameX733(526),
                         lossOfSignalX733(527),
                         materialSupplyExhausted(528),
                         multiplexerProblemX733(529),
                         outOfMemoryX733(530),
                         ouputDeviceError(531),
                         performanceDegraded(532),
                         powerProblems(533),
                         pressureUnacceptable(534),
                         processorProblems(535),
                         pumpFailureX733(536),
                         queueSizeExceeded(537),
                         receiveFailureX733(538),
                         receiverFailureX733(539),
                         remoteNodeTransmissionErrorX733(540),
                         resourceAtOrNearingCapacity(541),
                         responseTimeExecessive(542),
                         retransmissionRateExcessive(543),
                         softwareErrorX733(544),
                         softwareProgramAbnormallyTerminated(545),
                         softwareProgramError(546),
                         storageCapacityProblemX733(547),
                         temperatureUnacceptable(548),
                         thresholdCrossed(549),
                         timingProblemX733(550),
                         toxicLeakDetected(551),
                         transmitFailureX733(552),
                         transmiterFailure(553),
                         underlyingResourceUnavailable(554),
                         versionMismatchX733(555),
                         authenticationFailure(600),
                         breachOfConfidentiality(601),
                         cableTamper(602),
                         delayedInformation(603),
                         denialOfService(604),
                         duplicateInformation(605),
                         informationMissing(606),
                         informationModificationDetected(607),
                         informationOutOfSequence(608),
                         keyExpired(609),
                         nonRepudiationFailure(610),
                         outOfHoursActivity(611),
                         outOfService(612),
                         proceduralError(613),
                         unauthorizedAccessAttempt(614),
                         unexpectedInformation(615),
                         other(1024)
                     }

    SeverityValue ::= TEXTUAL-CONVENTION
        STATUS       current
        DESCRIPTION  "Severity (CCITT Rec. X.733)"
        SYNTAX       INTEGER {
                         cleared(1),
                         indetermine(2),
                         critical(3),
                         major(4),
                         minor(5),
                         warning(6),
                         notReport(7)
                     }

    UsedNotusedValue ::= TEXTUAL-CONVENTION
        STATUS       current
        DESCRIPTION  "Used/NotUsed Type"
        SYNTAX       INTEGER { invalid(0), notUsed(1), used(2) }

    ValidInvalidValue ::= TEXTUAL-CONVENTION
        STATUS       current
        DESCRIPTION  "Valid/Invalid Type"
        SYNTAX       INTEGER { invalid(0), valid(1) }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    summaryGroup OBJECT IDENTIFIER
        ::= { pasoNeoIpe-common 1 }

    trapGroup OBJECT IDENTIFIER
        ::= { pasoNeoIpe-common 2 }

    alarmStatusGroup OBJECT IDENTIFIER
        ::= { pasoNeoIpe-common 3 }

    inventoryGroup OBJECT IDENTIFIER
        ::= { pasoNeoIpe-common 7 }

    meteringGroup OBJECT IDENTIFIER
        ::= { pasoNeoIpe-common 8 }

    pmonGroup OBJECT IDENTIFIER
        ::= { pasoNeoIpe-common 9 }

    pmonTxRxLevGroup OBJECT IDENTIFIER
        ::= { pasoNeoIpe-common 10 }

    rmonGroup OBJECT IDENTIFIER
        ::= { pasoNeoIpe-common 11 }

-----------------------------------------------
-- summaryGroup Definitions
-----------------------------------------------

    alarmSummaryGroup OBJECT IDENTIFIER
        ::= { summaryGroup 1 }

    alarmSummaryCommonInfoTable OBJECT-TYPE
        SYNTAX       SEQUENCE OF AlarmSummaryCommonInfoEntry
        MAX-ACCESS   not-accessible
        STATUS       current
        DESCRIPTION  
            "Alarm Summary Table.
            Alarm Summary objects represents the maximum severity value of
            raised alarms of the entity."
        ::= { alarmSummaryGroup 1 }

    alarmSummaryCommonInfoEntry OBJECT-TYPE
        SYNTAX       AlarmSummaryCommonInfoEntry
        MAX-ACCESS   not-accessible
        STATUS       current
        DESCRIPTION  ""
        INDEX        { alarmSummaryCommonInfoIndex }
        ::= { alarmSummaryCommonInfoTable 1 }

    AlarmSummaryCommonInfoEntry ::= SEQUENCE {
        alarmSummaryCommonInfoIndex      Integer32,
        alarmSummaryCommonInfoNEAddress  IpAddress,
        alarmTotalSummary                SeverityValue,
        alarmIduSummary                  SeverityValue,
        alarmCtrlSummary                 SeverityValue,
        alarmOduSummary                  SeverityValue,
        alarmAuxInputSummary             SeverityValue,
        alarmPmonTcnSummary              SeverityValue,
        alarmRmonTcnSummary              SeverityValue,
        alarmRmonTcnCtrlSummary          SeverityValue
    }

    alarmSummaryCommonInfoIndex OBJECT-TYPE
        SYNTAX       Integer32 (1..1)
        MAX-ACCESS   not-accessible
        STATUS       current
        DESCRIPTION  "Index of this table"
        ::= { alarmSummaryCommonInfoEntry 1 }

    alarmSummaryCommonInfoNEAddress OBJECT-TYPE
        SYNTAX       IpAddress
        MAX-ACCESS   not-accessible
        STATUS       current
        DESCRIPTION  "reserved"
        ::= { alarmSummaryCommonInfoEntry 2 }

    alarmTotalSummary OBJECT-TYPE
        SYNTAX       SeverityValue
        MAX-ACCESS   read-only
        STATUS       current
        DESCRIPTION  "Total Summary Alarm."
        ::= { alarmSummaryCommonInfoEntry 3 }

    alarmIduSummary OBJECT-TYPE
        SYNTAX       SeverityValue
        MAX-ACCESS   read-only
        STATUS       current
        DESCRIPTION  "IDU Summary Alarm."
        ::= { alarmSummaryCommonInfoEntry 4 }

    alarmCtrlSummary OBJECT-TYPE
        SYNTAX       SeverityValue
        MAX-ACCESS   read-only
        STATUS       current
        DESCRIPTION  
            "Main Board / Ctrl Card Summary Alarm (including Equipment clock
            alarms)"
        ::= { alarmSummaryCommonInfoEntry 5 }

    alarmOduSummary OBJECT-TYPE
        SYNTAX       SeverityValue
        MAX-ACCESS   read-only
        STATUS       current
        DESCRIPTION  "ODU Summary Alarm."
        ::= { alarmSummaryCommonInfoEntry 6 }

    alarmAuxInputSummary OBJECT-TYPE
        SYNTAX       SeverityValue
        MAX-ACCESS   read-only
        STATUS       current
        DESCRIPTION  "AUX Input Summary Alarm."
        ::= { alarmSummaryCommonInfoEntry 7 }

    alarmPmonTcnSummary OBJECT-TYPE
        SYNTAX       SeverityValue
        MAX-ACCESS   read-only
        STATUS       current
        DESCRIPTION  "PMON TCN Summary Alarm."
        ::= { alarmSummaryCommonInfoEntry 8 }

    alarmRmonTcnSummary OBJECT-TYPE
        SYNTAX       SeverityValue
        MAX-ACCESS   read-only
        STATUS       current
        DESCRIPTION  "RMON TCN Summary Alarm."
        ::= { alarmSummaryCommonInfoEntry 9 }

    alarmRmonTcnCtrlSummary OBJECT-TYPE
        SYNTAX       SeverityValue
        MAX-ACCESS   read-only
        STATUS       current
        DESCRIPTION  "RMON TCN Main Board / Ctrl Card Summary Alarm."
        ::= { alarmSummaryCommonInfoEntry 10 }

    alarmSummaryIduGroup OBJECT IDENTIFIER
        ::= { alarmSummaryGroup 2 }

    alarmSummaryIduSlotInfoTable OBJECT-TYPE
        SYNTAX       SEQUENCE OF AlarmSummaryIduSlotInfoEntry
        MAX-ACCESS   not-accessible
        STATUS       current
        DESCRIPTION  "Alarm Summary per IDU Slot."
        ::= { alarmSummaryIduGroup 1 }

    alarmSummaryIduSlotInfoEntry OBJECT-TYPE
        SYNTAX       AlarmSummaryIduSlotInfoEntry
        MAX-ACCESS   not-accessible
        STATUS       current
        DESCRIPTION  ""
        INDEX        { alarmSummaryIduSlotInfoIndex }
        ::= { alarmSummaryIduSlotInfoTable 1 }

    AlarmSummaryIduSlotInfoEntry ::= SEQUENCE {
        alarmSummaryIduSlotInfoIndex      Integer32,
        alarmSummaryIduSlotInfoNEAddress  IpAddress,
        alarmIduSlotSummary               SeverityValue
    }

    alarmSummaryIduSlotInfoIndex OBJECT-TYPE
        SYNTAX       Integer32
        MAX-ACCESS   not-accessible
        STATUS       current
        DESCRIPTION  "Index of this table."
        ::= { alarmSummaryIduSlotInfoEntry 1 }

    alarmSummaryIduSlotInfoNEAddress OBJECT-TYPE
        SYNTAX       IpAddress
        MAX-ACCESS   not-accessible
        STATUS       current
        DESCRIPTION  "reserved."
        ::= { alarmSummaryIduSlotInfoEntry 2 }

    alarmIduSlotSummary OBJECT-TYPE
        SYNTAX       SeverityValue
        MAX-ACCESS   read-only
        STATUS       current
        DESCRIPTION  
            "IDU Slot Summary Alarm. the maximum severity value of raised
            alarms per slot."
        ::= { alarmSummaryIduSlotInfoEntry 3 }

    alarmSummaryOduInfoTable OBJECT-TYPE
        SYNTAX       SEQUENCE OF AlarmSummaryOduInfoEntry
        MAX-ACCESS   not-accessible
        STATUS       current
        DESCRIPTION  "Alarm Summary per ODU."
        ::= { alarmSummaryGroup 3 }

    alarmSummaryOduInfoEntry OBJECT-TYPE
        SYNTAX       AlarmSummaryOduInfoEntry
        MAX-ACCESS   not-accessible
        STATUS       current
        DESCRIPTION  ""
        INDEX        { alarmSummaryOduInfoIndex }
        ::= { alarmSummaryOduInfoTable 1 }

    AlarmSummaryOduInfoEntry ::= SEQUENCE {
        alarmSummaryOduInfoIndex      Integer32,
        alarmSummaryOduInfoNEAddress  IpAddress,
        alarmOduEachSummary           SeverityValue
    }

    alarmSummaryOduInfoIndex OBJECT-TYPE
        SYNTAX       Integer32
        MAX-ACCESS   not-accessible
        STATUS       current
        DESCRIPTION  "Index of this table"
        ::= { alarmSummaryOduInfoEntry 1 }

    alarmSummaryOduInfoNEAddress OBJECT-TYPE
        SYNTAX       IpAddress
        MAX-ACCESS   not-accessible
        STATUS       current
        DESCRIPTION  "reserved"
        ::= { alarmSummaryOduInfoEntry 2 }

    alarmOduEachSummary OBJECT-TYPE
        SYNTAX       SeverityValue
        MAX-ACCESS   read-only
        STATUS       current
        DESCRIPTION  
            "ODU Each Summary Alarm. the maximum severity value of raised
            alarms per ODU."
        ::= { alarmSummaryOduInfoEntry 3 }

    alarmSummaryPmonTcnInfoTable OBJECT-TYPE
        SYNTAX       SEQUENCE OF AlarmSummaryPmonTcnInfoEntry
        MAX-ACCESS   not-accessible
        STATUS       current
        DESCRIPTION  "Alarm Summay of Threshold Crossing Alarms per Slot."
        ::= { alarmSummaryGroup 4 }

    alarmSummaryPmonTcnInfoEntry OBJECT-TYPE
        SYNTAX       AlarmSummaryPmonTcnInfoEntry
        MAX-ACCESS   not-accessible
        STATUS       current
        DESCRIPTION  ""
        INDEX        { alarmSummaryPmonTcnInfoIndex }
        ::= { alarmSummaryPmonTcnInfoTable 1 }

    AlarmSummaryPmonTcnInfoEntry ::= SEQUENCE {
        alarmSummaryPmonTcnInfoIndex      Integer32,
        alarmSummaryPmonTcnInfoNEAddress  IpAddress,
        alarmPmonTcnSlotSummary           SeverityValue
    }

    alarmSummaryPmonTcnInfoIndex OBJECT-TYPE
        SYNTAX       Integer32
        MAX-ACCESS   not-accessible
        STATUS       current
        DESCRIPTION  "Index of this table."
        ::= { alarmSummaryPmonTcnInfoEntry 1 }

    alarmSummaryPmonTcnInfoNEAddress OBJECT-TYPE
        SYNTAX       IpAddress
        MAX-ACCESS   not-accessible
        STATUS       current
        DESCRIPTION  "reserved"
        ::= { alarmSummaryPmonTcnInfoEntry 2 }

    alarmPmonTcnSlotSummary OBJECT-TYPE
        SYNTAX       SeverityValue
        MAX-ACCESS   read-only
        STATUS       current
        DESCRIPTION  
            "PMON (TCN) Slot Summary Alarm. the maximum severity value of
            raised Threshold Crossing Alarms per slot."
        ::= { alarmSummaryPmonTcnInfoEntry 3 }

    alarmSummaryCtrlInfoTable OBJECT-TYPE
        SYNTAX       SEQUENCE OF AlarmSummaryCtrlInfoEntry
        MAX-ACCESS   not-accessible
        STATUS       current
        DESCRIPTION  "Alarm Summary of Main Board or Ctrl Card."
        ::= { alarmSummaryGroup 5 }

    alarmSummaryCtrlInfoEntry OBJECT-TYPE
        SYNTAX       AlarmSummaryCtrlInfoEntry
        MAX-ACCESS   not-accessible
        STATUS       current
        DESCRIPTION  ""
        INDEX        { alarmSummaryEoamInfoIndex }
        ::= { alarmSummaryCtrlInfoTable 1 }

    AlarmSummaryCtrlInfoEntry ::= SEQUENCE {
        alarmSummaryEoamInfoIndex      Integer32,
        alarmSummaryEoamInfoNEAddress  IpAddress,
        alarmEoamSummary               SeverityValue,
        alarmRmonEoamSummary           SeverityValue
    }

    alarmSummaryEoamInfoIndex OBJECT-TYPE
        SYNTAX       Integer32 (1..1)
        MAX-ACCESS   not-accessible
        STATUS       current
        DESCRIPTION  "Index of this table."
        ::= { alarmSummaryCtrlInfoEntry 1 }

    alarmSummaryEoamInfoNEAddress OBJECT-TYPE
        SYNTAX       IpAddress
        MAX-ACCESS   not-accessible
        STATUS       current
        DESCRIPTION  "reserved"
        ::= { alarmSummaryCtrlInfoEntry 2 }

    alarmEoamSummary OBJECT-TYPE
        SYNTAX       SeverityValue
        MAX-ACCESS   read-only
        STATUS       current
        DESCRIPTION  
            "ETH-OAM including MPLS-TP OAM Summary Alarm. The maximum
            severity value of raised alarms which are related to EtherOAM
            functions."
        ::= { alarmSummaryCtrlInfoEntry 3 }

    alarmRmonEoamSummary OBJECT-TYPE
        SYNTAX       SeverityValue
        MAX-ACCESS   read-only
        STATUS       current
        DESCRIPTION  
            "RMON ETH-OAM including MPLS-TP OAM Summary Alarm. The maximum
            severity value of raised alarms which are related to EtherOAM
            Threshold Crossing Alarms."
        ::= { alarmSummaryCtrlInfoEntry 4 }

    alarmSummaryRmonTcnInfoTable OBJECT-TYPE
        SYNTAX       SEQUENCE OF AlarmSummaryRmonTcnInfoEntry
        MAX-ACCESS   not-accessible
        STATUS       current
        DESCRIPTION  
            "Alarm summary of RMON Threshold Crossing Alarms per slot."
        ::= { alarmSummaryGroup 6 }

    alarmSummaryRmonTcnInfoEntry OBJECT-TYPE
        SYNTAX       AlarmSummaryRmonTcnInfoEntry
        MAX-ACCESS   not-accessible
        STATUS       current
        DESCRIPTION  ""
        INDEX        { alarmSummaryRmonTcnInfoIndex }
        ::= { alarmSummaryRmonTcnInfoTable 1 }

    AlarmSummaryRmonTcnInfoEntry ::= SEQUENCE {
        alarmSummaryRmonTcnInfoIndex      Integer32,
        alarmSummaryRmonTcnInfoNEAddress  IpAddress,
        alarmRmonTcnSlotSummary           SeverityValue
    }

    alarmSummaryRmonTcnInfoIndex OBJECT-TYPE
        SYNTAX       Integer32
        MAX-ACCESS   not-accessible
        STATUS       current
        DESCRIPTION  "Index of this table."
        ::= { alarmSummaryRmonTcnInfoEntry 1 }

    alarmSummaryRmonTcnInfoNEAddress OBJECT-TYPE
        SYNTAX       IpAddress
        MAX-ACCESS   not-accessible
        STATUS       current
        DESCRIPTION  "reserved."
        ::= { alarmSummaryRmonTcnInfoEntry 2 }

    alarmRmonTcnSlotSummary OBJECT-TYPE
        SYNTAX       SeverityValue
        MAX-ACCESS   read-only
        STATUS       current
        DESCRIPTION  
            "RMON (TCN) Slot Summary Alarm. The maximum value of raised
            alarms which are related RMON Threshold Crossing Alarm."
        ::= { alarmSummaryRmonTcnInfoEntry 3 }

    maintSummaryGroup OBJECT IDENTIFIER
        ::= { summaryGroup 2 }

    maintSummaryCommonInfoTable OBJECT-TYPE
        SYNTAX       SEQUENCE OF MaintSummaryCommonInfoEntry
        MAX-ACCESS   not-accessible
        STATUS       current
        DESCRIPTION  
            "This table represents the status of maintenance functions."
        ::= { maintSummaryGroup 1 }

    maintSummaryCommonInfoEntry OBJECT-TYPE
        SYNTAX       MaintSummaryCommonInfoEntry
        MAX-ACCESS   not-accessible
        STATUS       current
        DESCRIPTION  ""
        INDEX        { maintSummaryCommonInfoIndex }
        ::= { maintSummaryCommonInfoTable 1 }

    MaintSummaryCommonInfoEntry ::= SEQUENCE {
        maintSummaryCommonInfoIndex      Integer32,
        maintSummaryCommonInfoNEAddress  IpAddress,
        maintTotalSummary                OffOnValue
    }

    maintSummaryCommonInfoIndex OBJECT-TYPE
        SYNTAX       Integer32 (1..1)
        MAX-ACCESS   not-accessible
        STATUS       current
        DESCRIPTION  "Index of this table."
        ::= { maintSummaryCommonInfoEntry 1 }

    maintSummaryCommonInfoNEAddress OBJECT-TYPE
        SYNTAX       IpAddress
        MAX-ACCESS   not-accessible
        STATUS       current
        DESCRIPTION  "reserved"
        ::= { maintSummaryCommonInfoEntry 2 }

    maintTotalSummary OBJECT-TYPE
        SYNTAX       OffOnValue
        MAX-ACCESS   read-only
        STATUS       current
        DESCRIPTION  
            "Maintenance Total Summary. Represents the status of maintenance
            functions.
            'on' means some maintenance functions are performed on this
            equipment."
        ::= { maintSummaryCommonInfoEntry 3 }

-----------------------------------------------
-- trapGroup Definitions
-----------------------------------------------

    ipeTrapCommon OBJECT IDENTIFIER
        ::= { trapGroup 1 }

    ipeTrapCommonVars OBJECT IDENTIFIER
        ::= { ipeTrapCommon 1 }

    eventTotalCount OBJECT-TYPE
        SYNTAX       Counter32
        MAX-ACCESS   read-only
        STATUS       current
        DESCRIPTION  
            "The total count of SNMP TRAP/INFORM messages since this
            equipment was booted"
        ::= { ipeTrapCommonVars 1 }

    eventCount OBJECT-TYPE
        SYNTAX       Counter32
        MAX-ACCESS   read-only
        STATUS       current
        DESCRIPTION  
            "The count of SNMP TRAP/INFORM messages per event type
            (alarm/status/control) since this equipment was booted."
        ::= { ipeTrapCommonVars 2 }

    eventTime OBJECT-TYPE
        SYNTAX       DateAndTime
        MAX-ACCESS   read-only
        STATUS       current
        DESCRIPTION  
            "The local date and time when the TRAP/INFORM event occurred."
        ::= { ipeTrapCommonVars 3 }

    eventType OBJECT-TYPE
        SYNTAX       INTEGER {
                         alarmStateChage(1),
                         statusChange(2),
                         controlEvent(3)
                     }
        MAX-ACCESS   read-only
        STATUS       current
        DESCRIPTION  "The event type of TRAP/INFORM message."
        ::= { ipeTrapCommonVars 4 }

    eventResourceID OBJECT-TYPE
        SYNTAX       OBJECT IDENTIFIER
        MAX-ACCESS   read-only
        STATUS       current
        DESCRIPTION  
            "The OBJECT IDENTIFIER of the object which raised the event."
        ::= { ipeTrapCommonVars 5 }

    ipeTrapCommonAdditionalVars OBJECT IDENTIFIER
        ::= { ipeTrapCommon 2 }

    eventAdditionalText1 OBJECT-TYPE
        SYNTAX       DisplayString
        MAX-ACCESS   read-only
        STATUS       current
        DESCRIPTION  "Additional Information about the TRAP/INFORM event."
        ::= { ipeTrapCommonAdditionalVars 1 }

    eventAdditionalText2 OBJECT-TYPE
        SYNTAX       DisplayString
        MAX-ACCESS   read-only
        STATUS       current
        DESCRIPTION  "Additional Information about the TRAP/INFORM event."
        ::= { ipeTrapCommonAdditionalVars 2 }

    eventAdditionalText3 OBJECT-TYPE
        SYNTAX       DisplayString
        MAX-ACCESS   read-only
        STATUS       current
        DESCRIPTION  "Additional Information about the TRAP/INFORM event."
        ::= { ipeTrapCommonAdditionalVars 3 }

    eventAdditionalText4 OBJECT-TYPE
        SYNTAX       DisplayString
        MAX-ACCESS   read-only
        STATUS       current
        DESCRIPTION  "Additional Information about the TRAP/INFORM event."
        ::= { ipeTrapCommonAdditionalVars 4 }

    eventAdditionalText5 OBJECT-TYPE
        SYNTAX       DisplayString
        MAX-ACCESS   read-only
        STATUS       current
        DESCRIPTION  "Additional Information about the TRAP/INFORM event."
        ::= { ipeTrapCommonAdditionalVars 5 }

    ipeTrapAlarmVars OBJECT IDENTIFIER
        ::= { ipeTrapCommon 3 }

    eventSeverity OBJECT-TYPE
        SYNTAX       SeverityValue
        MAX-ACCESS   read-only
        STATUS       current
        DESCRIPTION  "Severity value of notified alarm event."
        ::= { ipeTrapAlarmVars 1 }

    eventAlarmType OBJECT-TYPE
        SYNTAX       AlarmTypeValue
        MAX-ACCESS   read-only
        STATUS       current
        DESCRIPTION  
            "Represents the X.733 based event type value for the alarms."
        ::= { ipeTrapAlarmVars 2 }

    eventProbableCause OBJECT-TYPE
        SYNTAX       ProbableCauseValue
        MAX-ACCESS   read-only
        STATUS       current
        DESCRIPTION  
            "Represents the X.733 based probable cause value for the alarms."
        ::= { ipeTrapAlarmVars 3 }

    ipeTrapStatusValueVars OBJECT IDENTIFIER
        ::= { ipeTrapCommon 4 }

    eventStatusValue OBJECT-TYPE
        SYNTAX       Integer32
        MAX-ACCESS   read-only
        STATUS       current
        DESCRIPTION  
            "the changed value of status object whose syntax is integer.
            Event object is represented by 'eventResourceID'"
        ::= { ipeTrapStatusValueVars 1 }

    eventStatusValueDspStr OBJECT-TYPE
        SYNTAX       DisplayString
        MAX-ACCESS   read-only
        STATUS       current
        DESCRIPTION  
            "the changed value of status object whose syntax is DISPLAY
            STRING. Event object is represented by 'eventResourceID'"
        ::= { ipeTrapStatusValueVars 2 }

    eventStatusValueOctStr OBJECT-TYPE
        SYNTAX       OCTET STRING (SIZE(0..512|32..32))
        MAX-ACCESS   read-only
        STATUS       current
        DESCRIPTION  
            "the changed value of status object whose syntax is OCTET STRING.
            Event object is represented by 'eventResourceID'
            
            SYNTAX:  OCTET STRING (SIZE(32..32))
            [iPASOLINK200/400/1000series/EX/iX],
                     OCTET STRING (SIZE(0..512)) [iPASOLINK VR series]"
        ::= { ipeTrapStatusValueVars 3 }

    eventStatusValueUnsigned32 OBJECT-TYPE
        SYNTAX       Unsigned32
        MAX-ACCESS   read-only
        STATUS       current
        DESCRIPTION  
            "the changed value of status object whose syntax is unsigned32.
            Event object is represented by 'eventResourceID'"
        ::= { ipeTrapStatusValueVars 4 }

    ipeTrapControlValueVars OBJECT IDENTIFIER
        ::= { ipeTrapCommon 5 }

    eventControlValue OBJECT-TYPE
        SYNTAX       Integer32
        MAX-ACCESS   read-only
        STATUS       current
        DESCRIPTION  
            "the changed value of control event whose syntax is integer32.
            Event object is represented by 'eventResourceID'"
        ::= { ipeTrapControlValueVars 1 }

    eventControlValueDspStr OBJECT-TYPE
        SYNTAX       DisplayString
        MAX-ACCESS   read-only
        STATUS       current
        DESCRIPTION  
            "the changed value of control event whose syntax is DISPLAY
            STRING. Event object is represented by 'eventResourceID'"
        ::= { ipeTrapControlValueVars 2 }

    eventControlValueOctStr OBJECT-TYPE
        SYNTAX       OCTET STRING (SIZE(0..512|32..32))
        MAX-ACCESS   read-only
        STATUS       current
        DESCRIPTION  
            "the changed value of control event whose syntax is OCTET STRING.
            Event object is represented by 'eventResourceID'
            value range:
            0 - 512 (iPASOLINK VR R5.0 or later),
            32 (others)"
        ::= { ipeTrapControlValueVars 3 }

    eventControlValueUnsigned32 OBJECT-TYPE
        SYNTAX       Unsigned32
        MAX-ACCESS   read-only
        STATUS       current
        DESCRIPTION  
            "the changed value of control event whose syntax is Unsigned32.
            Event object is represented by 'eventResourceID'"
        ::= { ipeTrapControlValueVars 4 }

    eventControlValueUnsigned64 OBJECT-TYPE
        SYNTAX       IpeUnsigned64
        MAX-ACCESS   read-only
        STATUS       current
        DESCRIPTION  
            "the changed value of control event whose syntax is
            IpeUnsigned64. Event object is represented by 'eventResourceID'"
        ::= { ipeTrapControlValueVars 5 }

    ipeTrapControlVars OBJECT IDENTIFIER
        ::= { ipeTrapCommon 6 }

    eventRecordUserName OBJECT-TYPE
        SYNTAX       DisplayString
        MAX-ACCESS   read-only
        STATUS       current
        DESCRIPTION  
            "the user name who triggered the control event. In SNMPv1/v2
            cases, this object reports 'unknown' unless 'ipeAccessUserName'
            is set within the SNMP SET PDU.
            In SNMPv3 cases, this object reports user name which is specified
            in SET-REQUEST."
        ::= { ipeTrapControlVars 1 }

    eventRecordAccessType OBJECT-TYPE
        SYNTAX       INTEGER {
                         invalid(0),
                         nms(1),
                         webLct(2),
                         cli(3),
                         internal(4)
                     }
        MAX-ACCESS   read-only
        STATUS       current
        DESCRIPTION  
            "the access type which triggered the control event. This object
            reports 'nms' unless 'ipeAccessType' is set within the SNMP SET
            PDU. Otherwise this object reports the same value of
            'ipeAccessType'.
            The value ipMplsCli(5) is valid for VR R6.0 or later."
        ::= { ipeTrapControlVars 2 }

    eventRecordAccessFrom OBJECT-TYPE
        SYNTAX       IpAddress
        MAX-ACCESS   read-only
        STATUS       current
        DESCRIPTION  
            "the ip address which triggered the control event. The ip address
            is normally recognized by source ip address of SET-REQUEST. But
            when 'ipeAccessFrom' is set in the SET-REQUEST, this object
            reports same value of 'ipeAccessFrom'."
        ::= { ipeTrapControlVars 3 }

    eventRecordAccessFromV6 OBJECT-TYPE
        SYNTAX       Ipv6Address
        MAX-ACCESS   read-only
        STATUS       current
        DESCRIPTION  
            "the IPv6 address which triggered the control event. The IPv6
            address is normally recognized by source IPv6 address of
            SET-REQUEST. But when 'ipeAccessFromV6Address' is set in the
            SET-REQUEST, this object reports same value of
            'ipeAccessFromV6Address'."
        ::= { ipeTrapControlVars 4 }

    ipeTrapFileDownloadValueVars OBJECT IDENTIFIER
        ::= { ipeTrapCommon 7 }

    eventDownloadModule OBJECT-TYPE
        SYNTAX       Integer32
        MAX-ACCESS   read-only
        STATUS       current
        DESCRIPTION  
            "Represents download module type which triggered download event.
            The type values are same as 'ipeSysOpFileDownloadModule'."
        ::= { ipeTrapFileDownloadValueVars 1 }

    eventDownloadStatus OBJECT-TYPE
        SYNTAX       Integer32
        MAX-ACCESS   read-only
        STATUS       current
        DESCRIPTION  
            "Represents download status. The status values are same as
            'ipeSysOpFileDownloadStatus'."
        ::= { ipeTrapFileDownloadValueVars 2 }

    eventUpdateDetail OBJECT-TYPE
        SYNTAX       DisplayString
        MAX-ACCESS   read-only
        STATUS       current
        DESCRIPTION  
            "Represents download file name which is specified by
            'ipeFsUpdateFileDetail'."
        ::= { ipeTrapFileDownloadValueVars 3 }

    eventUpdateStatus OBJECT-TYPE
        SYNTAX       Integer32
        MAX-ACCESS   read-only
        STATUS       current
        DESCRIPTION  
            "Represents download file progress. The value is same as
            'ipeFsUpdateFileStatus'."
        ::= { ipeTrapFileDownloadValueVars 4 }

    ipeTrapItemVar OBJECT IDENTIFIER
        ::= { trapGroup 3 }

    ipeAlarmTrapItemVar OBJECT IDENTIFIER
        ::= { ipeTrapItemVar 1 }

    alarmStateChange NOTIFICATION-TYPE
        OBJECTS      {
                         eventTotalCount,
                         eventCount,
                         eventTime,
                         eventType,
                         eventResourceID,
                         eventSeverity,
                         eventAlarmType,
                         eventProbableCause,
                         eventAdditionalText1,
                         eventAdditionalText2,
                         eventAdditionalText3,
                         eventAdditionalText4,
                         eventAdditionalText5
                     }
        STATUS       current
        DESCRIPTION  
            "Trap for Alarm
            This notification reports that a processed alarm status may have
            changed.
            The object information is recorded in 'eventResourceID' and also
            changed alarm status is recorded in 'eventSeverity'.
            The 'eventTotalCount' and 'eventCount' is sequential number.
            'eventTotalCount' is notification event count since agent was
            booted.
            'eventAdditionalText' provides some event description."
        ::= { ipeAlarmTrapItemVar 1 }

    ipeStatusTrapItemVar OBJECT IDENTIFIER
        ::= { ipeTrapItemVar 2 }

    statusChange NOTIFICATION-TYPE
        OBJECTS      {
                         eventTotalCount,
                         eventCount,
                         eventTime,
                         eventType,
                         eventResourceID,
                         eventStatusValue,
                         eventAdditionalText1,
                         eventAdditionalText2,
                         eventAdditionalText3,
                         eventAdditionalText4,
                         eventAdditionalText5
                     }
        STATUS       current
        DESCRIPTION  
            "Trap for Status (Integer)
            This notification reports that the object's status whose SYNTAX
            is INTEGER type may have changed.
            The object information is recorded in 'eventResourceID'.
            The 'eventTotalCount' and 'eventCount' is sequential number.
            'eventTotalCount' is notification event count since agent was
            booted.
            'eventAdditionalText' provides some event description."
        ::= { ipeStatusTrapItemVar 1 }

    statusChangeDspStr NOTIFICATION-TYPE
        OBJECTS      {
                         eventTotalCount,
                         eventCount,
                         eventTime,
                         eventType,
                         eventResourceID,
                         eventStatusValueDspStr,
                         eventAdditionalText1,
                         eventAdditionalText2,
                         eventAdditionalText3,
                         eventAdditionalText4,
                         eventAdditionalText5
                     }
        STATUS       current
        DESCRIPTION  
            "Trap for Status (Display String)
            This notification reports that the object's status whose SYNTAX
            is DISPLAY STRING type may have changed.
            The object information is recorded in 'eventResourceID'.
            The 'eventTotalCount' and 'eventCount' is sequential number.
            'eventTotalCount' is notification event count since agent was
            booted.
            'eventAdditionalText' provides some event description."
        ::= { ipeStatusTrapItemVar 2 }

    statusChangeOctStr NOTIFICATION-TYPE
        OBJECTS      {
                         eventTotalCount,
                         eventCount,
                         eventTime,
                         eventType,
                         eventResourceID,
                         eventStatusValueOctStr,
                         eventAdditionalText1,
                         eventAdditionalText2,
                         eventAdditionalText3,
                         eventAdditionalText4,
                         eventAdditionalText5
                     }
        STATUS       current
        DESCRIPTION  
            "Trap for Status (Octet String)
            This notification reports that the object's status whose SYNTAX
            is OCTET STRING type may have changed.
            The object information is recorded in 'eventResourceID'.
            The 'eventTotalCount' and 'eventCount' is sequential number.
            'eventTotalCount' is notification event count since agent was
            booted.
            'eventAdditionalText' provides some event description."
        ::= { ipeStatusTrapItemVar 3 }

    statusChangeUnsigned32 NOTIFICATION-TYPE
        OBJECTS      {
                         eventTotalCount,
                         eventCount,
                         eventTime,
                         eventType,
                         eventResourceID,
                         eventStatusValueUnsigned32,
                         eventAdditionalText1,
                         eventAdditionalText2,
                         eventAdditionalText3,
                         eventAdditionalText4,
                         eventAdditionalText5
                     }
        STATUS       current
        DESCRIPTION  
            "Trap for Status (Unsigned32)
            This notification reports that the object's status whose SYNTAX
            is Unsigned type may have changed.
            The object information is recorded in 'eventResourceID' and also
            changed alarm status is recorded in 'eventSeverity'.
            The 'eventTotalCount' and 'eventCount' is sequential number.
            'eventTotalCount' is notification event count since agent was
            booted.
            'eventAdditionalText' provides some event description."
        ::= { ipeStatusTrapItemVar 4 }

    ipeControlTrapItemVar OBJECT IDENTIFIER
        ::= { ipeTrapItemVar 3 }

    controlEvent NOTIFICATION-TYPE
        OBJECTS      {
                         eventTotalCount,
                         eventCount,
                         eventTime,
                         eventType,
                         eventResourceID,
                         eventControlValue,
                         eventRecordUserName,
                         eventRecordAccessType,
                         eventRecordAccessFrom,
                         eventAdditionalText1,
                         eventAdditionalText2,
                         eventAdditionalText3,
                         eventAdditionalText4,
                         eventAdditionalText5,
                         eventRecordAccessFromV6
                     }
        STATUS       current
        DESCRIPTION  
            "Trap for Control (Integer)
            This notification reports that the object's value is changed by
            snmp-set request.
            The object information is recorded in 'eventResourceID' and also
            changed value is recorded in 'eventControlValue'.
            The 'eventTotalCount' and 'eventCount' is sequential number.
            'eventTotalCount' is notification event count since agent was
            booted.
            'eventAdditionalText' provides some event description."
        ::= { ipeControlTrapItemVar 1 }

    controlEventDspStr NOTIFICATION-TYPE
        OBJECTS      {
                         eventTotalCount,
                         eventCount,
                         eventTime,
                         eventType,
                         eventResourceID,
                         eventControlValueDspStr,
                         eventRecordUserName,
                         eventRecordAccessType,
                         eventRecordAccessFrom,
                         eventAdditionalText1,
                         eventAdditionalText2,
                         eventAdditionalText3,
                         eventAdditionalText4,
                         eventAdditionalText5,
                         eventRecordAccessFromV6
                     }
        STATUS       current
        DESCRIPTION  
            "Trap for Control (Display String)
            This notification reports that the object's value is changed by
            snmp-set request.
            The object information is recorded in 'eventResourceID' and also
            changed value is recorded in 'eventControlValueDspStr'.
            The 'eventTotalCount' and 'eventCount' is sequential number.
            'eventTotalCount' is notification event count since agent was
            booted.
            'eventAdditionalText' provides some event description."
        ::= { ipeControlTrapItemVar 2 }

    controlEventOctStr NOTIFICATION-TYPE
        OBJECTS      {
                         eventTotalCount,
                         eventCount,
                         eventTime,
                         eventType,
                         eventResourceID,
                         eventControlValueOctStr,
                         eventRecordUserName,
                         eventRecordAccessType,
                         eventRecordAccessFrom,
                         eventAdditionalText1,
                         eventAdditionalText2,
                         eventAdditionalText3,
                         eventAdditionalText4,
                         eventAdditionalText5,
                         eventRecordAccessFromV6
                     }
        STATUS       current
        DESCRIPTION  
            "Trap for Control (Octet String)
            This notification reports that the object's value is changed by
            snmp-set request.
            The object information is recorded in 'eventResourceID' and also
            changed value is recorded in 'eventControlValueOctStr'.
            The 'eventTotalCount' and 'eventCount' is sequential number.
            'eventTotalCount' is notification event count since agent was
            booted.
            'eventAdditionalText' provides some event description."
        ::= { ipeControlTrapItemVar 3 }

    controlEventUnsigned32 NOTIFICATION-TYPE
        OBJECTS      {
                         eventTotalCount,
                         eventCount,
                         eventTime,
                         eventType,
                         eventResourceID,
                         eventControlValueUnsigned32,
                         eventRecordUserName,
                         eventRecordAccessType,
                         eventRecordAccessFrom,
                         eventAdditionalText1,
                         eventAdditionalText2,
                         eventAdditionalText3,
                         eventAdditionalText4,
                         eventAdditionalText5,
                         eventRecordAccessFromV6
                     }
        STATUS       current
        DESCRIPTION  
            "Trap for Control (Unsigned32)
            This notification reports that the object's value is changed by
            snmp-set request.
            The object information is recorded in 'eventResourceID' and also
            changed value is recorded in 'eventControlValueUnsigned32'.
            The 'eventTotalCount' and 'eventCount' is sequential number.
            'eventTotalCount' is notification event count since agent was
            booted.
            'eventAdditionalText' provides some event description."
        ::= { ipeControlTrapItemVar 4 }

    controlEventUnsigned64 NOTIFICATION-TYPE
        OBJECTS      {
                         eventTotalCount,
                         eventCount,
                         eventTime,
                         eventType,
                         eventResourceID,
                         eventControlValueUnsigned64,
                         eventRecordUserName,
                         eventRecordAccessType,
                         eventRecordAccessFrom,
                         eventAdditionalText1,
                         eventAdditionalText2,
                         eventAdditionalText3,
                         eventAdditionalText4,
                         eventAdditionalText5,
                         eventRecordAccessFromV6
                     }
        STATUS       current
        DESCRIPTION  
            "Trap for Control (IpeUnsigned64)
            This notification reports that the object's value is changed by
            snmp-set request.
            The object information is recorded in 'eventResourceID' and also
            changed value is recorded in 'eventControlValueUnsigned64'.
            The 'eventTotalCount' and 'eventCount' is sequential number.
            'eventTotalCount' is notification event count since agent was
            booted.
            'eventAdditionalText' provides some event description."
        ::= { ipeControlTrapItemVar 5 }

    ipeFileDownloadTrapItemVar OBJECT IDENTIFIER
        ::= { ipeTrapItemVar 4 }

    fileDownloadEvent NOTIFICATION-TYPE
        OBJECTS      {
                         eventTotalCount,
                         eventCount,
                         eventTime,
                         eventType,
                         eventResourceID,
                         eventDownloadModule,
                         eventDownloadStatus,
                         eventAdditionalText1,
                         eventAdditionalText2,
                         eventAdditionalText3,
                         eventAdditionalText4,
                         eventAdditionalText5
                     }
        STATUS       current
        DESCRIPTION  
            "Trap for File Download
            This notification reports that the executed download status is
            changed. Changed value is recorded in 'eventDownloadStatus'. The
            'eventTotalCount' and 'eventCount' is sequential number.
            'eventTotalCount' is notification event count since agent was
            booted.
            'eventAdditionalText' provides some event description."
        ::= { ipeFileDownloadTrapItemVar 1 }

    fileUpdateEvent NOTIFICATION-TYPE
        OBJECTS      {
                         eventTotalCount,
                         eventCount,
                         eventTime,
                         eventType,
                         eventResourceID,
                         eventUpdateDetail,
                         eventUpdateStatus,
                         eventAdditionalText1,
                         eventAdditionalText2,
                         eventAdditionalText3,
                         eventAdditionalText4,
                         eventAdditionalText5
                     }
        STATUS       current
        DESCRIPTION  
            "Trap for File Update
            This notification reports that the executed file update status is
            changed. Changed value is recorded in 'eventUpdateStatus'. The
            'eventTotalCount' and 'eventCount' is sequential number.
            'eventTotalCount' is notification event count since agent was
            booted.
            'eventAdditionalText' provides some event description."
        ::= { ipeFileDownloadTrapItemVar 2 }

    ipeEventGroup OBJECT IDENTIFIER
        ::= { trapGroup 4 }

    eventTable OBJECT-TYPE
        SYNTAX       SEQUENCE OF EventEntry
        MAX-ACCESS   not-accessible
        STATUS       current
        DESCRIPTION  
            "This table represents trap counter value of each event type."
        ::= { ipeEventGroup 1 }

    eventEntry OBJECT-TYPE
        SYNTAX       EventEntry
        MAX-ACCESS   not-accessible
        STATUS       current
        DESCRIPTION  ""
        INDEX        { eventIndex }
        ::= { eventTable 1 }

    EventEntry ::= SEQUENCE {
        eventIndex        INTEGER,
        eventNEAddress    IpAddress,
        eventDescription  DisplayString,
        eventCounter      Counter32,
        eventLastTime     DateAndTime
    }

    eventIndex OBJECT-TYPE
        SYNTAX       INTEGER {
                         alarmStateChage(1),
                         statusChange(2),
                         controlEvent(3)
                     }
        MAX-ACCESS   not-accessible
        STATUS       current
        DESCRIPTION  "Index of this table."
        ::= { eventEntry 1 }

    eventNEAddress OBJECT-TYPE
        SYNTAX       IpAddress
        MAX-ACCESS   not-accessible
        STATUS       current
        DESCRIPTION  "reserved"
        ::= { eventEntry 2 }

    eventDescription OBJECT-TYPE
        SYNTAX       DisplayString
        MAX-ACCESS   read-only
        STATUS       current
        DESCRIPTION  "A textual string information about the event."
        ::= { eventEntry 3 }

    eventCounter OBJECT-TYPE
        SYNTAX       Counter32
        MAX-ACCESS   read-only
        STATUS       current
        DESCRIPTION  
            "The count of SNMP TRAP/INFORM messages per event type
            (alarm/status/control) since this equipment was booted."
        ::= { eventEntry 4 }

    eventLastTime OBJECT-TYPE
        SYNTAX       DateAndTime
        MAX-ACCESS   read-only
        STATUS       current
        DESCRIPTION  
            "The date and time when this event type was last updated."
        ::= { eventEntry 5 }

    eventTypeTable OBJECT-TYPE
        SYNTAX       SEQUENCE OF EventTypeEntry
        MAX-ACCESS   not-accessible
        STATUS       current
        DESCRIPTION  "This table represents event information."
        ::= { ipeEventGroup 2 }

    eventTypeEntry OBJECT-TYPE
        SYNTAX       EventTypeEntry
        MAX-ACCESS   not-accessible
        STATUS       current
        DESCRIPTION  ""
        INDEX        {
                         eventTypeIndex,
                         eventTypeSourceCategory,
                         eventTypeElemId
                     }
        ::= { eventTypeTable 1 }

    EventTypeEntry ::= SEQUENCE {
        eventTypeIndex           Integer32,
        eventTypeSourceCategory  Integer32,
        eventTypeElemId          Integer32,
        eventTypeNEAddress       IpAddress,
        eventTypeTrapId          Integer32,
        eventTypeDescription     DisplayString,
        eventTypeRowStatus       RowStatus
    }

    eventTypeIndex OBJECT-TYPE
        SYNTAX       Integer32
        MAX-ACCESS   not-accessible
        STATUS       current
        DESCRIPTION  
            "index of this table. The value is same as 'eventType'."
        ::= { eventTypeEntry 1 }

    eventTypeSourceCategory OBJECT-TYPE
        SYNTAX       Integer32
        MAX-ACCESS   not-accessible
        STATUS       current
        DESCRIPTION  
            "Index of this table. This object represents category of
            generator of the event."
        ::= { eventTypeEntry 2 }

    eventTypeElemId OBJECT-TYPE
        SYNTAX       Integer32
        MAX-ACCESS   not-accessible
        STATUS       current
        DESCRIPTION  
            "Index of this table. Administrative index value of the event
            which is uniquely identified among the eventTypeSourceCategory."
        ::= { eventTypeEntry 3 }

    eventTypeNEAddress OBJECT-TYPE
        SYNTAX       IpAddress
        MAX-ACCESS   not-accessible
        STATUS       current
        DESCRIPTION  "reserved."
        ::= { eventTypeEntry 4 }

    eventTypeTrapId OBJECT-TYPE
        SYNTAX       Integer32
        MAX-ACCESS   read-only
        STATUS       current
        DESCRIPTION  
            "Represents event type id same as eventTypeIndex. This object
            indicates which counter will be incremented when this event
            occurs."
        ::= { eventTypeEntry 5 }

    eventTypeDescription OBJECT-TYPE
        SYNTAX       DisplayString
        MAX-ACCESS   read-only
        STATUS       current
        DESCRIPTION  "A Textual string information about the event."
        ::= { eventTypeEntry 6 }

    eventTypeRowStatus OBJECT-TYPE
        SYNTAX       RowStatus
        MAX-ACCESS   read-create
        STATUS       current
        DESCRIPTION  
            "RowStatus of this table. This table is created automatically
            when the agent starts, and cannot create or destroy from
            manager."
        ::= { eventTypeEntry 7 }

    ipeTrapStatusGroup OBJECT IDENTIFIER
        ::= { trapGroup 5 }

    ipeTrapCounterTable OBJECT-TYPE
        SYNTAX       SEQUENCE OF IpeTrapCounterEntry
        MAX-ACCESS   not-accessible
        STATUS       current
        DESCRIPTION  "This table represents event total count."
        ::= { ipeTrapStatusGroup 1 }

    ipeTrapCounterEntry OBJECT-TYPE
        SYNTAX       IpeTrapCounterEntry
        MAX-ACCESS   not-accessible
        STATUS       current
        DESCRIPTION  ""
        INDEX        { ipeTrapCounterIndex }
        ::= { ipeTrapCounterTable 1 }

    IpeTrapCounterEntry ::= SEQUENCE {
        ipeTrapCounterIndex           Integer32,
        ipeTrapTotalCounterNEAddress  IpAddress,
        ipeTrapTotalCounter           Counter32
    }

    ipeTrapCounterIndex OBJECT-TYPE
        SYNTAX       Integer32
        MAX-ACCESS   not-accessible
        STATUS       current
        DESCRIPTION  "Index of this table."
        ::= { ipeTrapCounterEntry 1 }

    ipeTrapTotalCounterNEAddress OBJECT-TYPE
        SYNTAX       IpAddress
        MAX-ACCESS   not-accessible
        STATUS       current
        DESCRIPTION  "reserved."
        ::= { ipeTrapCounterEntry 2 }

    ipeTrapTotalCounter OBJECT-TYPE
        SYNTAX       Counter32
        MAX-ACCESS   read-only
        STATUS       current
        DESCRIPTION  
            "represents total counter value which counts all event type of
            TRAP/INFORM messages."
        ::= { ipeTrapCounterEntry 3 }

-----------------------------------------------
-- alarmStatusGroup Definitions
-----------------------------------------------

    asOduGroup OBJECT IDENTIFIER
        ::= { alarmStatusGroup 1 }

    oduGroupTable OBJECT-TYPE
        SYNTAX       SEQUENCE OF OduGroupEntry
        MAX-ACCESS   not-accessible
        STATUS       current
        DESCRIPTION  "This table represents alarm and status information."
        ::= { asOduGroup 1 }

    oduGroupEntry OBJECT-TYPE
        SYNTAX       OduGroupEntry
        MAX-ACCESS   not-accessible
        STATUS       current
        DESCRIPTION  ""
        INDEX        { oduGroupIfIndex }
        ::= { oduGroupTable 1 }

    OduGroupEntry ::= SEQUENCE {
        oduGroupIfIndex    InterfaceIndex,
        oduGroupNEAddress  IpAddress,
        oduAlarm           SeverityValue,
        txPowerAlarm       SeverityValue,
        txInputAlarm       SeverityValue,
        rxLevelAlarm       SeverityValue,
        cpuCableOpenAlarm  SeverityValue,
        loRefAlarm         SeverityValue,
        muteStatus         OffOnValue,
        oduPsAlarm         SeverityValue,
        oduPsSetStatus     OffOnValue,
        oduTypeMismatch    SeverityValue,
        oduTotalAlarm      SeverityValue
    }

    oduGroupIfIndex OBJECT-TYPE
        SYNTAX       InterfaceIndex
        MAX-ACCESS   not-accessible
        STATUS       current
        DESCRIPTION  "Index of this table."
        ::= { oduGroupEntry 1 }

    oduGroupNEAddress OBJECT-TYPE
        SYNTAX       IpAddress
        MAX-ACCESS   not-accessible
        STATUS       current
        DESCRIPTION  "reserved."
        ::= { oduGroupEntry 2 }

    oduAlarm OBJECT-TYPE
        SYNTAX       SeverityValue
        MAX-ACCESS   read-only
        STATUS       current
        DESCRIPTION  "ODU Alarm."
        ::= { oduGroupEntry 3 }

    txPowerAlarm OBJECT-TYPE
        SYNTAX       SeverityValue
        MAX-ACCESS   read-only
        STATUS       current
        DESCRIPTION  "ODU TX Power Alarm."
        ::= { oduGroupEntry 4 }

    txInputAlarm OBJECT-TYPE
        SYNTAX       SeverityValue
        MAX-ACCESS   read-only
        STATUS       current
        DESCRIPTION  "ODU TX Input Alarm."
        ::= { oduGroupEntry 5 }

    rxLevelAlarm OBJECT-TYPE
        SYNTAX       SeverityValue
        MAX-ACCESS   read-only
        STATUS       current
        DESCRIPTION  "ODU RX Level Alarm."
        ::= { oduGroupEntry 6 }

    cpuCableOpenAlarm OBJECT-TYPE
        SYNTAX       SeverityValue
        MAX-ACCESS   read-only
        STATUS       current
        DESCRIPTION  "ODU CPU / Cable Open Alarm."
        ::= { oduGroupEntry 7 }

    loRefAlarm OBJECT-TYPE
        SYNTAX       SeverityValue
        MAX-ACCESS   read-only
        STATUS       current
        DESCRIPTION  "ODU LO REF Alarm"
        ::= { oduGroupEntry 8 }

    muteStatus OBJECT-TYPE
        SYNTAX       OffOnValue
        MAX-ACCESS   read-only
        STATUS       current
        DESCRIPTION  "ODU mute status."
        ::= { oduGroupEntry 9 }

    oduPsAlarm OBJECT-TYPE
        SYNTAX       SeverityValue
        MAX-ACCESS   read-only
        STATUS       current
        DESCRIPTION  "ODU Power Supply Alarm"
        ::= { oduGroupEntry 10 }

    oduPsSetStatus OBJECT-TYPE
        SYNTAX       OffOnValue
        MAX-ACCESS   read-only
        STATUS       current
        DESCRIPTION  "ODU Power Supply Status."
        ::= { oduGroupEntry 11 }

    oduTypeMismatch OBJECT-TYPE
        SYNTAX       SeverityValue
        MAX-ACCESS   read-only
        STATUS       current
        DESCRIPTION  "ODU Type Mismatch Alarm."
        ::= { oduGroupEntry 12 }

    oduTotalAlarm OBJECT-TYPE
        SYNTAX       SeverityValue
        MAX-ACCESS   read-only
        STATUS       obsolete
        DESCRIPTION  "ODU Total Alarm."
        ::= { oduGroupEntry 13 }

    asModemGroup OBJECT IDENTIFIER
        ::= { alarmStatusGroup 2 }

    modemGroupTable OBJECT-TYPE
        SYNTAX       SEQUENCE OF ModemGroupEntry
        MAX-ACCESS   not-accessible
        STATUS       current
        DESCRIPTION  
            "This table represents MODEM Alarm Status information."
        ::= { asModemGroup 1 }

    modemGroupEntry OBJECT-TYPE
        SYNTAX       ModemGroupEntry
        MAX-ACCESS   not-accessible
        STATUS       current
        DESCRIPTION  ""
        INDEX        { modemGroupIfIndex }
        ::= { modemGroupTable 1 }

    ModemGroupEntry ::= SEQUENCE {
        modemGroupIfIndex    InterfaceIndex,
        modemGroupNEAddress  IpAddress,
        lof                  SeverityValue,
        frameID              SeverityValue,
        highBERAlarm         SeverityValue,
        lowBERAlarm          SeverityValue,
        earlyWarningAlarm    SeverityValue,
        modAlarm             SeverityValue,
        ifCableShortAlarm    SeverityValue,
        atpcPowerMode        INTEGER,
        inPhaseStatus        INTEGER,
        amrRangeMismatch     SeverityValue,
        txModulation         INTEGER,
        rxModulation         INTEGER,
        l2SyncLossAlarm      SeverityValue,
        rdiAlarm             SeverityValue,
        uaeAlarm             SeverityValue,
        unlocked             SeverityValue,
        tempAlarm            SeverityValue,
        tdmRangeMismatch     SeverityValue,
        modemPsOff           OffOnValue
    }

    modemGroupIfIndex OBJECT-TYPE
        SYNTAX       InterfaceIndex
        MAX-ACCESS   not-accessible
        STATUS       current
        DESCRIPTION  "Index of this table"
        ::= { modemGroupEntry 1 }

    modemGroupNEAddress OBJECT-TYPE
        SYNTAX       IpAddress
        MAX-ACCESS   not-accessible
        STATUS       current
        DESCRIPTION  "reserved"
        ::= { modemGroupEntry 2 }

    lof OBJECT-TYPE
        SYNTAX       SeverityValue
        MAX-ACCESS   read-only
        STATUS       current
        DESCRIPTION  "MODEM LOF Alarm"
        ::= { modemGroupEntry 3 }

    frameID OBJECT-TYPE
        SYNTAX       SeverityValue
        MAX-ACCESS   read-only
        STATUS       current
        DESCRIPTION  "MODEM Frame ID Alarm"
        ::= { modemGroupEntry 4 }

    highBERAlarm OBJECT-TYPE
        SYNTAX       SeverityValue
        MAX-ACCESS   read-only
        STATUS       current
        DESCRIPTION  "MODEM High BER Alarm."
        ::= { modemGroupEntry 5 }

    lowBERAlarm OBJECT-TYPE
        SYNTAX       SeverityValue
        MAX-ACCESS   read-only
        STATUS       current
        DESCRIPTION  "MODEM Low BER Alarm."
        ::= { modemGroupEntry 6 }

    earlyWarningAlarm OBJECT-TYPE
        SYNTAX       SeverityValue
        MAX-ACCESS   read-only
        STATUS       current
        DESCRIPTION  "MODEM Early Warning Alarm"
        ::= { modemGroupEntry 7 }

    modAlarm OBJECT-TYPE
        SYNTAX       SeverityValue
        MAX-ACCESS   read-only
        STATUS       current
        DESCRIPTION  "MODEM MOD Alarm"
        ::= { modemGroupEntry 8 }

    ifCableShortAlarm OBJECT-TYPE
        SYNTAX       SeverityValue
        MAX-ACCESS   read-only
        STATUS       current
        DESCRIPTION  "MODEM IF Cable Short Alarm"
        ::= { modemGroupEntry 9 }

    atpcPowerMode OBJECT-TYPE
        SYNTAX       INTEGER { stop(1), active(2) }
        MAX-ACCESS   read-only
        STATUS       current
        DESCRIPTION  "MODEM ATPC Power Mode Status"
        ::= { modemGroupEntry 10 }

    inPhaseStatus OBJECT-TYPE
        SYNTAX       INTEGER { inphase(1), outphase(2) }
        MAX-ACCESS   read-only
        STATUS       current
        DESCRIPTION  "MODEM Inphase Status"
        ::= { modemGroupEntry 11 }

    amrRangeMismatch OBJECT-TYPE
        SYNTAX       SeverityValue
        MAX-ACCESS   read-only
        STATUS       obsolete
        DESCRIPTION  "obsoleted"
        ::= { modemGroupEntry 12 }

    txModulation OBJECT-TYPE
        SYNTAX       INTEGER {
                         invalid(0),
                         qpsk(1),
                         qam16(2),
                         qam32(3),
                         qam64(4),
                         qam128(5),
                         qam256(6),
                         qam512(7),
                         qam1024(8),
                         psk8(11),
                         qpskOneFourthsBW(15),
                         qpskOneHalfBW(16)
                     }
        MAX-ACCESS   read-only
        STATUS       current
        DESCRIPTION  "MODEM TX Modulation Status"
        ::= { modemGroupEntry 13 }

    rxModulation OBJECT-TYPE
        SYNTAX       INTEGER {
                         invalid(0),
                         qpsk(1),
                         qam16(2),
                         qam32(3),
                         qam64(4),
                         qam128(5),
                         qam256(6),
                         qam512(7),
                         qam1024(8),
                         psk8(11),
                         qpskOneFourthsBW(15),
                         qpskOneHalfBW(16)
                     }
        MAX-ACCESS   read-only
        STATUS       current
        DESCRIPTION  "MODEM RX Modulation Status."
        ::= { modemGroupEntry 14 }

    l2SyncLossAlarm OBJECT-TYPE
        SYNTAX       SeverityValue
        MAX-ACCESS   read-only
        STATUS       current
        DESCRIPTION  "MODEM L2SYNC Loss Alarm."
        ::= { modemGroupEntry 15 }

    rdiAlarm OBJECT-TYPE
        SYNTAX       SeverityValue
        MAX-ACCESS   read-only
        STATUS       current
        DESCRIPTION  "MODEM RDI Alarm"
        ::= { modemGroupEntry 16 }

    uaeAlarm OBJECT-TYPE
        SYNTAX       SeverityValue
        MAX-ACCESS   read-only
        STATUS       current
        DESCRIPTION  "MODEM UAE Alarm"
        ::= { modemGroupEntry 17 }

    unlocked OBJECT-TYPE
        SYNTAX       SeverityValue
        MAX-ACCESS   read-only
        STATUS       current
        DESCRIPTION  "MODEM Unlocked Alarm"
        ::= { modemGroupEntry 18 }

    tempAlarm OBJECT-TYPE
        SYNTAX       SeverityValue
        MAX-ACCESS   read-only
        STATUS       obsolete
        DESCRIPTION  "MODEM Temperature Alarm"
        ::= { modemGroupEntry 19 }

    tdmRangeMismatch OBJECT-TYPE
        SYNTAX       SeverityValue
        MAX-ACCESS   read-only
        STATUS       current
        DESCRIPTION  "MODEM TDM / AMR / AMBR Range Mismatch Alarm"
        ::= { modemGroupEntry 20 }

    modemPsOff OBJECT-TYPE
        SYNTAX       OffOnValue
        MAX-ACCESS   read-only
        STATUS       obsolete
        DESCRIPTION  "MDOEM Power Supply Status"
        ::= { modemGroupEntry 21 }

    modemXpicTable OBJECT-TYPE
        SYNTAX       SEQUENCE OF ModemXpicEntry
        MAX-ACCESS   not-accessible
        STATUS       current
        DESCRIPTION  "Represents XPIC Alarm and Status"
        ::= { asModemGroup 2 }

    modemXpicEntry OBJECT-TYPE
        SYNTAX       ModemXpicEntry
        MAX-ACCESS   not-accessible
        STATUS       current
        DESCRIPTION  ""
        INDEX        { modemXpicIfIndex }
        ::= { modemXpicTable 1 }

    ModemXpicEntry ::= SEQUENCE {
        modemXpicIfIndex          InterfaceIndex,
        modemXpicNEAddress        IpAddress,
        xIFLevelAlarm             SeverityValue,
        xpicTypeMismatch          SeverityValue,
        xpicPairMuteModeMismatch  SeverityValue
    }

    modemXpicIfIndex OBJECT-TYPE
        SYNTAX       InterfaceIndex
        MAX-ACCESS   not-accessible
        STATUS       current
        DESCRIPTION  "Index of this table"
        ::= { modemXpicEntry 1 }

    modemXpicNEAddress OBJECT-TYPE
        SYNTAX       IpAddress
        MAX-ACCESS   not-accessible
        STATUS       current
        DESCRIPTION  "reserved."
        ::= { modemXpicEntry 2 }

    xIFLevelAlarm OBJECT-TYPE
        SYNTAX       SeverityValue
        MAX-ACCESS   read-only
        STATUS       current
        DESCRIPTION  "MODEM XIF Alarm."
        ::= { modemXpicEntry 3 }

    xpicTypeMismatch OBJECT-TYPE
        SYNTAX       SeverityValue
        MAX-ACCESS   read-only
        STATUS       current
        DESCRIPTION  "MODEM XPIC Mode Mismatch Alarm."
        ::= { modemXpicEntry 4 }

    xpicPairMuteModeMismatch OBJECT-TYPE
        SYNTAX       SeverityValue
        MAX-ACCESS   read-only
        STATUS       current
        DESCRIPTION  "MODEM XPIC Pair Mute Mode Mismatch Alarm."
        ::= { modemXpicEntry 5 }

    modemCardTable OBJECT-TYPE
        SYNTAX       SEQUENCE OF ModemCardEntry
        MAX-ACCESS   not-accessible
        STATUS       current
        DESCRIPTION  "Represents MODEM Card Alarm Status."
        ::= { asModemGroup 3 }

    modemCardEntry OBJECT-TYPE
        SYNTAX       ModemCardEntry
        MAX-ACCESS   not-accessible
        STATUS       current
        DESCRIPTION  ""
        INDEX        { modemCardIndex }
        ::= { modemCardTable 1 }

    ModemCardEntry ::= SEQUENCE {
        modemCardIndex         Integer32,
        modemCardNEAddress     IpAddress,
        modemComFailAlarm      SeverityValue,
        modemUnequipped        SeverityValue,
        modemAlarm             SeverityValue,
        modemBusErrorTx        SeverityValue,
        modemBusErrorRx        SeverityValue,
        modemTypeMismatch      SeverityValue,
        modemCardOnlineStatus  INTEGER,
        modemCardPsAlarm       SeverityValue
    }

    modemCardIndex OBJECT-TYPE
        SYNTAX       Integer32
        MAX-ACCESS   not-accessible
        STATUS       current
        DESCRIPTION  "Index of this table."
        ::= { modemCardEntry 1 }

    modemCardNEAddress OBJECT-TYPE
        SYNTAX       IpAddress
        MAX-ACCESS   not-accessible
        STATUS       current
        DESCRIPTION  "reserved"
        ::= { modemCardEntry 2 }

    modemComFailAlarm OBJECT-TYPE
        SYNTAX       SeverityValue
        MAX-ACCESS   read-only
        STATUS       current
        DESCRIPTION  "MODEM Communication FAIL Alarm."
        ::= { modemCardEntry 3 }

    modemUnequipped OBJECT-TYPE
        SYNTAX       SeverityValue
        MAX-ACCESS   read-only
        STATUS       obsolete
        DESCRIPTION  "MODEM Unequipped Alarm."
        ::= { modemCardEntry 4 }

    modemAlarm OBJECT-TYPE
        SYNTAX       SeverityValue
        MAX-ACCESS   read-only
        STATUS       current
        DESCRIPTION  "MODEM Module Alarm."
        ::= { modemCardEntry 5 }

    modemBusErrorTx OBJECT-TYPE
        SYNTAX       SeverityValue
        MAX-ACCESS   read-only
        STATUS       current
        DESCRIPTION  "MODEM Tx Bus Error Alarm."
        ::= { modemCardEntry 6 }

    modemBusErrorRx OBJECT-TYPE
        SYNTAX       SeverityValue
        MAX-ACCESS   read-only
        STATUS       current
        DESCRIPTION  "MODEM Rx Bus Error Alarm."
        ::= { modemCardEntry 7 }

    modemTypeMismatch OBJECT-TYPE
        SYNTAX       SeverityValue
        MAX-ACCESS   read-only
        STATUS       obsolete
        DESCRIPTION  "MODEM Type Mismatch Alarm."
        ::= { modemCardEntry 8 }

    modemCardOnlineStatus OBJECT-TYPE
        SYNTAX       INTEGER { invalid(0), offline(1), online(2) }
        MAX-ACCESS   read-only
        STATUS       current
        DESCRIPTION  "MODEM Online Status"
        ::= { modemCardEntry 9 }

    modemCardPsAlarm OBJECT-TYPE
        SYNTAX       SeverityValue
        MAX-ACCESS   read-only
        STATUS       obsolete
        DESCRIPTION  "MODEM Power Supply Alarm."
        ::= { modemCardEntry 10 }

    asModemHeaderCompressTable OBJECT-TYPE
        SYNTAX       SEQUENCE OF AsModemHeaderCompressEntry
        MAX-ACCESS   not-accessible
        STATUS       current
        DESCRIPTION  
            "Header Compression Function Status.
            This table is created automatically when the Modem Card is
            provisioned, if the F/W supports the new Header Compression
            function."
        ::= { asModemGroup 4 }

    asModemHeaderCompressEntry OBJECT-TYPE
        SYNTAX       AsModemHeaderCompressEntry
        MAX-ACCESS   not-accessible
        STATUS       current
        DESCRIPTION  ""
        INDEX        { asModemHeaderCompressIfIndex }
        ::= { asModemHeaderCompressTable 1 }

    AsModemHeaderCompressEntry ::= SEQUENCE {
        asModemHeaderCompressIfIndex      InterfaceIndex,
        asModemHeaderCompressNEAddress    IpAddress,
        asModemHeaderCompressMismatch     SeverityValue,
        asModemHeaderCompressCurrentMode  INTEGER,
        asModemHeaderCompressVersion      Integer32
    }

    asModemHeaderCompressIfIndex OBJECT-TYPE
        SYNTAX       InterfaceIndex
        MAX-ACCESS   not-accessible
        STATUS       current
        DESCRIPTION  "Index of this table."
        ::= { asModemHeaderCompressEntry 1 }

    asModemHeaderCompressNEAddress OBJECT-TYPE
        SYNTAX       IpAddress
        MAX-ACCESS   not-accessible
        STATUS       current
        DESCRIPTION  "reserved."
        ::= { asModemHeaderCompressEntry 2 }

    asModemHeaderCompressMismatch OBJECT-TYPE
        SYNTAX       SeverityValue
        MAX-ACCESS   read-only
        STATUS       current
        DESCRIPTION  
            "Header/Payload* Compression Mismatch Alarm.
            If the configuration of local and remote header compression mode
            is different, the alarm will be reported.
            (*iPASOLINK VR series only)"
        ::= { asModemHeaderCompressEntry 3 }

    asModemHeaderCompressCurrentMode OBJECT-TYPE
        SYNTAX       INTEGER {
                         invalid(0),
                         disable(1),
                         enhancedMacWithIpv4(6),
                         enhancedMacWithIpv6(7),
                         enhancedMacWithMpls(8),
                         macWithVlan(9),
                         payload(33),
                         payloadMac(34),
                         payloadMacWithIpv4(35),
                         payloadMacWithIpv6(36),
                         payloadMacWithMpls(37)
                     }
        MAX-ACCESS   read-only
        STATUS       current
        DESCRIPTION  
            "Current Header/Payload* Compression Mode.
            This value shows same value as 'provModemHeaderCompressMode'
            usually. But the value will be different from
            'provModemHeaderCompressMode', when the new Header Compression
            Function is configured to the old Modem Card (which does not have
            new Header Compression capabilities)
            (*iPASOLINK VR series only)"
        ::= { asModemHeaderCompressEntry 4 }

    asModemHeaderCompressVersion OBJECT-TYPE
        SYNTAX       Integer32
        MAX-ACCESS   read-only
        STATUS       current
        DESCRIPTION  
            "The version of Header/Payload* Compression Function.
             '1' means the Header Compression is not supported and the
            Payload* Compression is not supported.
             '2' means the Header Compression is supported and the Payload*
            Compression is not supported.
             '3' means the Header Compression is not supported and the
            Payload* Compression is supported.
             '4' means the Header Compression is supported and the Payload*
            Compression is supported.
            (*iPASOLINK VR series only)"
        ::= { asModemHeaderCompressEntry 5 }

    asModemHeaderCompressRemoteTable OBJECT-TYPE
        SYNTAX       SEQUENCE OF AsModemHeaderCompressRemoteEntry
        MAX-ACCESS   not-accessible
        STATUS       current
        DESCRIPTION  
            "Remote Modem Header Compression Function Status.
            This table is created automatically when the Modem Card is
            provisioned, if the F/W supports the new Header Compression
            function."
        ::= { asModemGroup 5 }

    asModemHeaderCompressRemoteEntry OBJECT-TYPE
        SYNTAX       AsModemHeaderCompressRemoteEntry
        MAX-ACCESS   not-accessible
        STATUS       current
        DESCRIPTION  ""
        INDEX        { asModemHeaderCompressRemoteIfIndex }
        ::= { asModemHeaderCompressRemoteTable 1 }

    AsModemHeaderCompressRemoteEntry ::= SEQUENCE {
        asModemHeaderCompressRemoteIfIndex    InterfaceIndex,
        asModemHeaderCompressRemoteNEAddress  IpAddress,
        asModemHeaderCompressRemoteMode       INTEGER,
        asModemHeaderCompressRemoteVlanMode   INTEGER,
        asModemHeaderCompressRemoteVersion    Integer32
    }

    asModemHeaderCompressRemoteIfIndex OBJECT-TYPE
        SYNTAX       InterfaceIndex
        MAX-ACCESS   not-accessible
        STATUS       current
        DESCRIPTION  "Index of this table."
        ::= { asModemHeaderCompressRemoteEntry 1 }

    asModemHeaderCompressRemoteNEAddress OBJECT-TYPE
        SYNTAX       IpAddress
        MAX-ACCESS   not-accessible
        STATUS       current
        DESCRIPTION  "reserved."
        ::= { asModemHeaderCompressRemoteEntry 2 }

    asModemHeaderCompressRemoteMode OBJECT-TYPE
        SYNTAX       INTEGER {
                         invalid(0),
                         disable(1),
                         enhancedMacWithIpv4(6),
                         enhancedMacWithIpv6(7),
                         enhancedMacWithMpls(8),
                         macWithVlan(9),
                         payload(33),
                         payloadMac(34),
                         payloadMacWithIpv4(35),
                         payloadMacWithIpv6(36),
                         payloadMacWithMpls(37),
                         unknown(99)
                     }
        MAX-ACCESS   read-only
        STATUS       current
        DESCRIPTION  
            "Header/Payload* Compression Mode of Remote Modem.
            When the Radio link is not established, the value will be changed
            to 'unknown'.
            (*iPASOLINK VR series only)"
        ::= { asModemHeaderCompressRemoteEntry 3 }

    asModemHeaderCompressRemoteVlanMode OBJECT-TYPE
        SYNTAX       INTEGER { invalid(0), dot1q(1), dot1ad(2), unknown(99) }
        MAX-ACCESS   read-only
        STATUS       current
        DESCRIPTION  
            "VLAN Mode of Remote equipment.
            When the Radio link is not established, the object will show the
            value 'unknown'."
        ::= { asModemHeaderCompressRemoteEntry 4 }

    asModemHeaderCompressRemoteVersion OBJECT-TYPE
        SYNTAX       Integer32
        MAX-ACCESS   read-only
        STATUS       current
        DESCRIPTION  
            "The version of Header/Payload* Compression Function for the
            Remote Modem.
             '1' means the Header Compression is not supported and the
            Payload* Compression is not supported.
             '2' means the Header Compression is supported and the Payload*
            Compression is not supported.
             '3' means the Header Compression is not supported and the
            Payload* Compression is supported.
             '4' means the Header Compression is supported and the Payload*
            Compression is supported.
            
            When the Radio link is not established, the object will return
            '99'.
            If the object returns other value, the local node cannot
            recognize the received value from remote node.
            (*iPASOLINK VR series only)"
        ::= { asModemHeaderCompressRemoteEntry 5 }

    asModemTrafficAggrTable OBJECT-TYPE
        SYNTAX       SEQUENCE OF AsModemTrafficAggrEntry
        MAX-ACCESS   not-accessible
        STATUS       current
        DESCRIPTION  
            "This table contains alarm and status object for Radio Traffic
            Aggregation mode."
        ::= { asModemGroup 6 }

    asModemTrafficAggrEntry OBJECT-TYPE
        SYNTAX       AsModemTrafficAggrEntry
        MAX-ACCESS   not-accessible
        STATUS       current
        DESCRIPTION  ""
        INDEX        { asModemTrafficAggrIfIndex }
        ::= { asModemTrafficAggrTable 1 }

    AsModemTrafficAggrEntry ::= SEQUENCE {
        asModemTrafficAggrIfIndex       InterfaceIndex,
        asModemTrafficAggrNEAddress     IpAddress,
        asModemTrafficAggrModeMismatch  SeverityValue,
        asModemTrafficAggrVersion       Integer32,
        asModemTrafficAggrEncapStatus   INTEGER
    }

    asModemTrafficAggrIfIndex OBJECT-TYPE
        SYNTAX       InterfaceIndex
        MAX-ACCESS   not-accessible
        STATUS       current
        DESCRIPTION  
            "Index of this table. This table is created automatically when
            the MODEM card is provisioned."
        ::= { asModemTrafficAggrEntry 1 }

    asModemTrafficAggrNEAddress OBJECT-TYPE
        SYNTAX       IpAddress
        MAX-ACCESS   not-accessible
        STATUS       current
        DESCRIPTION  "reserved."
        ::= { asModemTrafficAggrEntry 2 }

    asModemTrafficAggrModeMismatch OBJECT-TYPE
        SYNTAX       SeverityValue
        MAX-ACCESS   read-only
        STATUS       current
        DESCRIPTION  
            "Radio Traffic Aggregation Mode Mismatch Alarm.
            This alarm is asserted if the Radio Traffic Aggregation is
            configured when the H/W and/or F/W does not support the function.
            And also the alarm is asserted when the configuration is
            mismatched between local node and peer node."
        ::= { asModemTrafficAggrEntry 3 }

    asModemTrafficAggrVersion OBJECT-TYPE
        SYNTAX       Integer32
        MAX-ACCESS   read-only
        STATUS       current
        DESCRIPTION  
            "The support version of Radio Traffic Aggreation function.
             '5' means the physical advanced mode aggregation, physical mode
                 aggregation, and legacy radio traffic aggregation are
                 supported (valid for iPASO VR 10 only)
             '2' means the physical mode aggregation and legacy radio traffic
                 aggregation are supported
             '1' means the legacy radio traffic aggregation is supported 
                 but physical mode is not supported.
             '0' means the physical mode and legacy radio traffic aggregation
                 are not supported
                 (license is not installed or Modem card does not have that
            capability).
            When EXA is configuration of RTA, this value is 2 ."
        ::= { asModemTrafficAggrEntry 4 }

    asModemTrafficAggrEncapStatus OBJECT-TYPE
        SYNTAX       INTEGER { invalid(0), normal(1), fail(2) }
        MAX-ACCESS   read-only
        STATUS       current
        DESCRIPTION  
            "Radio Traffic Aggregation Encapsulation Status.
            When the Modem cannot build frames continuously, the object will
            assert the 'fail'.
            The value will change to 'normal' if the condition is cleared."
        ::= { asModemTrafficAggrEntry 5 }

    asModemTransmissionModeTable OBJECT-TYPE
        SYNTAX       SEQUENCE OF AsModemTransmissionModeEntry
        MAX-ACCESS   not-accessible
        STATUS       current
        DESCRIPTION  
            "This table contains Alarm & Status for Modem transmission Mode."
        ::= { asModemGroup 7 }

    asModemTransmissionModeEntry OBJECT-TYPE
        SYNTAX       AsModemTransmissionModeEntry
        MAX-ACCESS   not-accessible
        STATUS       current
        DESCRIPTION  ""
        INDEX        { asModemTransmissionModeCardIndex }
        ::= { asModemTransmissionModeTable 1 }

    AsModemTransmissionModeEntry ::= SEQUENCE {
        asModemTransmissionModeCardIndex          Integer32,
        asModemTransmissionModeNEAddress          IpAddress,
        asModemTransmissionModeMismatch           SeverityValue,
        asModemTransparentClockModeMismatch       SeverityValue,
        asModemTransparentClockCalibrationStatus  INTEGER,
        asModemDelayEqualizerSettingMismatch      SeverityValue,
        asModemTransparentClockFail               SeverityValue
    }

    asModemTransmissionModeCardIndex OBJECT-TYPE
        SYNTAX       Integer32
        MAX-ACCESS   not-accessible
        STATUS       current
        DESCRIPTION  
            "Index of this table. This table is created automatically when
            the appropriate MODEM card is provisioned."
        ::= { asModemTransmissionModeEntry 1 }

    asModemTransmissionModeNEAddress OBJECT-TYPE
        SYNTAX       IpAddress
        MAX-ACCESS   not-accessible
        STATUS       current
        DESCRIPTION  "reserved"
        ::= { asModemTransmissionModeEntry 2 }

    asModemTransmissionModeMismatch OBJECT-TYPE
        SYNTAX       SeverityValue
        MAX-ACCESS   read-only
        STATUS       current
        DESCRIPTION  
            "This object indicates the Transmission Mode Mismatch Alarm.
            When the local system and remote system are configured different
            transmission mode, or the H/W which does not have the capability
            for 'lowPDV' is configured as 'LowPDV', the object will report
            alarm."
        ::= { asModemTransmissionModeEntry 3 }

    asModemTransparentClockModeMismatch OBJECT-TYPE
        SYNTAX       SeverityValue
        MAX-ACCESS   read-only
        STATUS       current
        DESCRIPTION  
            "This object indicates the Transparent Clock Mode Mismatch Alarm.
            When the local system and remote system are configured different
            transparent clock mode mismatch, or the H/W which does not have
            the capability for 'transparent clock mode' is configured as
            'TransparentClockMode', the object will report alarm."
        ::= { asModemTransmissionModeEntry 4 }

    asModemTransparentClockCalibrationStatus OBJECT-TYPE
        SYNTAX       INTEGER { invalid(0), unlocked(1), locked(2) }
        MAX-ACCESS   read-only
        STATUS       current
        DESCRIPTION  
            "This object indicates the calibration status of Transparent
            Clock as Modem Physical interface. This object is valid only when
            Transparent Clock Mode is enabled and the Mode is correspond
            version."
        ::= { asModemTransmissionModeEntry 5 }

    asModemDelayEqualizerSettingMismatch OBJECT-TYPE
        SYNTAX       SeverityValue
        MAX-ACCESS   read-only
        STATUS       current
        DESCRIPTION  "Delay Equalizer Setting Mismatch."
        ::= { asModemTransmissionModeEntry 6 }

    asModemTransparentClockFail OBJECT-TYPE
        SYNTAX       SeverityValue
        MAX-ACCESS   read-only
        STATUS       obsolete
        DESCRIPTION  
            "reserved. (This object indicates the calibration status of
            Transparent Clock. This object is valid only when Transparent
            Clock Mode is enabled and the Mode is correspond version.)"
        ::= { asModemTransmissionModeEntry 7 }

    asModemEncryptionTable OBJECT-TYPE
        SYNTAX       SEQUENCE OF AsModemEncryptionEntry
        MAX-ACCESS   not-accessible
        STATUS       current
        DESCRIPTION  
            "This table contains Alarm & Status for RADIO encryption."
        ::= { asModemGroup 8 }

    asModemEncryptionEntry OBJECT-TYPE
        SYNTAX       AsModemEncryptionEntry
        MAX-ACCESS   not-accessible
        STATUS       current
        DESCRIPTION  ""
        INDEX        { asModemEncryptionIfIndex }
        ::= { asModemEncryptionTable 1 }

    AsModemEncryptionEntry ::= SEQUENCE {
        asModemEncryptionIfIndex          InterfaceIndex,
        asModemEncryptionNEAddress        IpAddress,
        asModemEncryptionModeMismatch     SeverityValue,
        asModemEncryptionDecryptFail      SeverityValue,
        asModemEncryptionPskState         SeverityValue,
        asModemEncryptionKeyExchangeFail  SeverityValue
    }

    asModemEncryptionIfIndex OBJECT-TYPE
        SYNTAX       InterfaceIndex
        MAX-ACCESS   not-accessible
        STATUS       current
        DESCRIPTION  "Index of this table."
        ::= { asModemEncryptionEntry 1 }

    asModemEncryptionNEAddress OBJECT-TYPE
        SYNTAX       IpAddress
        MAX-ACCESS   not-accessible
        STATUS       current
        DESCRIPTION  "reserved"
        ::= { asModemEncryptionEntry 2 }

    asModemEncryptionModeMismatch OBJECT-TYPE
        SYNTAX       SeverityValue
        MAX-ACCESS   read-only
        STATUS       current
        DESCRIPTION  "This object indicates the Mode Mismatch Alarm."
        ::= { asModemEncryptionEntry 3 }

    asModemEncryptionDecryptFail OBJECT-TYPE
        SYNTAX       SeverityValue
        MAX-ACCESS   read-only
        STATUS       current
        DESCRIPTION  "This object indicates the Decrypt Fail Alarm."
        ::= { asModemEncryptionEntry 4 }

    asModemEncryptionPskState OBJECT-TYPE
        SYNTAX       SeverityValue
        MAX-ACCESS   read-only
        STATUS       current
        DESCRIPTION  "This object indicates the Psk State Alarm."
        ::= { asModemEncryptionEntry 5 }

    asModemEncryptionKeyExchangeFail OBJECT-TYPE
        SYNTAX       SeverityValue
        MAX-ACCESS   read-only
        STATUS       current
        DESCRIPTION  "This object indicates the Key Exchange Fail Alarm."
        ::= { asModemEncryptionEntry 6 }

    asClkGroup OBJECT IDENTIFIER
        ::= { alarmStatusGroup 5 }

    clkCommonTable OBJECT-TYPE
        SYNTAX       SEQUENCE OF ClkCommonEntry
        MAX-ACCESS   not-accessible
        STATUS       current
        DESCRIPTION  "Represents Main Board / Ctrl Card CLK Status."
        ::= { asClkGroup 1 }

    clkCommonEntry OBJECT-TYPE
        SYNTAX       ClkCommonEntry
        MAX-ACCESS   not-accessible
        STATUS       current
        DESCRIPTION  ""
        INDEX        { clkCommonIndex }
        ::= { clkCommonTable 1 }

    ClkCommonEntry ::= SEQUENCE {
        clkCommonIndex             INTEGER,
        clkCommonNEAddress         IpAddress,
        ltiAlarm                   SeverityValue,
        refClkChange               INTEGER,
        extClkLoop                 SeverityValue,
        currentTimingSource        INTEGER,
        timingSourceCondition      INTEGER,
        timingSourceControlStatus  INTEGER
    }

    clkCommonIndex OBJECT-TYPE
        SYNTAX       INTEGER { clk(1) }
        MAX-ACCESS   not-accessible
        STATUS       current
        DESCRIPTION  
            "Index of this table. The value is same as Main Board or Ctrl
            Card."
        ::= { clkCommonEntry 1 }

    clkCommonNEAddress OBJECT-TYPE
        SYNTAX       IpAddress
        MAX-ACCESS   not-accessible
        STATUS       current
        DESCRIPTION  "reserved."
        ::= { clkCommonEntry 2 }

    ltiAlarm OBJECT-TYPE
        SYNTAX       SeverityValue
        MAX-ACCESS   read-only
        STATUS       current
        DESCRIPTION  "Main Board / Ctrl Card LTI Alarm."
        ::= { clkCommonEntry 3 }

    refClkChange OBJECT-TYPE
        SYNTAX       INTEGER {
                         lockedRef1(1),
                         lockedRef2(2),
                         lockedRef3(3),
                         holdover(4),
                         freerun(5)
                     }
        MAX-ACCESS   read-only
        STATUS       current
        DESCRIPTION  "Main Board / Ctrl Card CLK Status."
        ::= { clkCommonEntry 4 }

    extClkLoop OBJECT-TYPE
        SYNTAX       SeverityValue
        MAX-ACCESS   read-only
        STATUS       current
        DESCRIPTION  "Main Board / Ctrl Card EXT CLK Timing Loop Alarm."
        ::= { clkCommonEntry 5 }

    currentTimingSource OBJECT-TYPE
        SYNTAX       INTEGER { selectRef1(1), selectRef2(2), selectRef3(3) }
        MAX-ACCESS   read-only
        STATUS       current
        DESCRIPTION  "Main Board / Ctrl Card Current Timing Source."
        ::= { clkCommonEntry 6 }

    timingSourceCondition OBJECT-TYPE
        SYNTAX       INTEGER { locked(1), holdover(2), freerun(3) }
        MAX-ACCESS   read-only
        STATUS       current
        DESCRIPTION  "Main Board / Ctrl Card Timing Source Status."
        ::= { clkCommonEntry 7 }

    timingSourceControlStatus OBJECT-TYPE
        SYNTAX       INTEGER { auto(1), manualSelect(2), forcedSelect(3) }
        MAX-ACCESS   read-only
        STATUS       current
        DESCRIPTION  "Main Board / Ctrl Card Timing Source Switch Status."
        ::= { clkCommonEntry 8 }

    clkRefTable OBJECT-TYPE
        SYNTAX       SEQUENCE OF ClkRefEntry
        MAX-ACCESS   not-accessible
        STATUS       current
        DESCRIPTION  "Represents Timing Source Status."
        ::= { asClkGroup 2 }

    clkRefEntry OBJECT-TYPE
        SYNTAX       ClkRefEntry
        MAX-ACCESS   not-accessible
        STATUS       current
        DESCRIPTION  ""
        INDEX        { clkRefIndex }
        ::= { clkRefTable 1 }

    ClkRefEntry ::= SEQUENCE {
        clkRefIndex        INTEGER,
        clkRefNEAddress    IpAddress,
        clkFailedAlarm     SeverityValue,
        clkDriftAlarm      SeverityValue,
        clkRefFailedAlarm  SeverityValue,
        refLockoutStatus   INTEGER,
        refQL              INTEGER
    }

    clkRefIndex OBJECT-TYPE
        SYNTAX       INTEGER { refclk1(1), refclk2(2), refclk3(3) }
        MAX-ACCESS   not-accessible
        STATUS       current
        DESCRIPTION  
            "Index of this table. The table is created per each timing
            source."
        ::= { clkRefEntry 1 }

    clkRefNEAddress OBJECT-TYPE
        SYNTAX       IpAddress
        MAX-ACCESS   not-accessible
        STATUS       current
        DESCRIPTION  "reserved"
        ::= { clkRefEntry 2 }

    clkFailedAlarm OBJECT-TYPE
        SYNTAX       SeverityValue
        MAX-ACCESS   read-only
        STATUS       current
        DESCRIPTION  
            "Main Board / Ctrl Card CLK FAIL Alarm per CLK Reference."
        ::= { clkRefEntry 3 }

    clkDriftAlarm OBJECT-TYPE
        SYNTAX       SeverityValue
        MAX-ACCESS   read-only
        STATUS       current
        DESCRIPTION  
            "Main Board / Ctrl Card CLK Drift Alarm per CLK Reference."
        ::= { clkRefEntry 4 }

    clkRefFailedAlarm OBJECT-TYPE
        SYNTAX       SeverityValue
        MAX-ACCESS   read-only
        STATUS       current
        DESCRIPTION  
            "Main Board / Ctrl Card SSM FAIL Alarm per CLK Reference."
        ::= { clkRefEntry 5 }

    refLockoutStatus OBJECT-TYPE
        SYNTAX       INTEGER { lockout(1), normal(2) }
        MAX-ACCESS   read-only
        STATUS       current
        DESCRIPTION  
            "Main Board / Ctrl Card Lockout Status per CLK Reference."
        ::= { clkRefEntry 6 }

    refQL OBJECT-TYPE
        SYNTAX       INTEGER {
                         qlPrc(1),
                         qlSsuA(2),
                         qlSsuB(3),
                         qlOriginal(4),
                         qlSec(5),
                         qlDnu(6),
                         qlInvx(7),
                         qlFailed(8),
                         notAvail(9),
                         qlPrs(20),
                         qlStu(21),
                         qlSt2(22),
                         qlTnc(23),
                         qlSt3e(24),
                         qlSt3(25),
                         qlSmc(26),
                         qlSt4(27)
                     }
        MAX-ACCESS   read-only
        STATUS       current
        DESCRIPTION  
            "Main Board / Ctrl Card Quality level per CLK Reference."
        ::= { clkRefEntry 7 }

    asExtClkGroup OBJECT IDENTIFIER
        ::= { alarmStatusGroup 6 }

    extClkGroupTable OBJECT-TYPE
        SYNTAX       SEQUENCE OF ExtClkGroupEntry
        MAX-ACCESS   not-accessible
        STATUS       current
        DESCRIPTION  "Represents Ext CLK Alarm / Status."
        ::= { asExtClkGroup 1 }

    extClkGroupEntry OBJECT-TYPE
        SYNTAX       ExtClkGroupEntry
        MAX-ACCESS   not-accessible
        STATUS       current
        DESCRIPTION  ""
        INDEX        { extClkGroupIndex }
        ::= { extClkGroupTable 1 }

    ExtClkGroupEntry ::= SEQUENCE {
        extClkGroupIndex      INTEGER,
        extClkGroupNEAddress  IpAddress,
        clk2mLosAlarm         SeverityValue,
        aisAlarm              SeverityValue,
        lofAlarm              SeverityValue,
        clk2mUnequipped       SeverityValue,
        extClkOutputStatus    INTEGER,
        extClkOutputQlValue   INTEGER,
        squelch               INTEGER,
        clk2mTypeMismatch     SeverityValue
    }

    extClkGroupIndex OBJECT-TYPE
        SYNTAX       INTEGER { extclk(1) }
        MAX-ACCESS   not-accessible
        STATUS       current
        DESCRIPTION  "Index of this table."
        ::= { extClkGroupEntry 1 }

    extClkGroupNEAddress OBJECT-TYPE
        SYNTAX       IpAddress
        MAX-ACCESS   not-accessible
        STATUS       current
        DESCRIPTION  "reserved."
        ::= { extClkGroupEntry 2 }

    clk2mLosAlarm OBJECT-TYPE
        SYNTAX       SeverityValue
        MAX-ACCESS   read-only
        STATUS       current
        DESCRIPTION  "Main Board / Ctrl Card EXT CLK LOS Alarm."
        ::= { extClkGroupEntry 3 }

    aisAlarm OBJECT-TYPE
        SYNTAX       SeverityValue
        MAX-ACCESS   read-only
        STATUS       current
        DESCRIPTION  "Main Board / Ctrl Card EXT CLK AIS Alarm."
        ::= { extClkGroupEntry 4 }

    lofAlarm OBJECT-TYPE
        SYNTAX       SeverityValue
        MAX-ACCESS   read-only
        STATUS       current
        DESCRIPTION  "Main Board / Ctrl Card EXT CLK LOF Alarm."
        ::= { extClkGroupEntry 5 }

    clk2mUnequipped OBJECT-TYPE
        SYNTAX       SeverityValue
        MAX-ACCESS   read-only
        STATUS       obsolete
        DESCRIPTION  "Main Board / Ctrl Card EXT CLK Unequipped Alarm."
        ::= { extClkGroupEntry 6 }

    extClkOutputStatus OBJECT-TYPE
        SYNTAX       INTEGER { normal(1), ais(2), shutdown(3) }
        MAX-ACCESS   read-only
        STATUS       current
        DESCRIPTION  "Main Board / Ctrl Card EXT CLK Output Status."
        ::= { extClkGroupEntry 7 }

    extClkOutputQlValue OBJECT-TYPE
        SYNTAX       INTEGER {
                         qlPrc(1),
                         qlSsuA(2),
                         qlSsuB(3),
                         qlOriginal(4),
                         qlSec(5),
                         qlDnu(6),
                         qlInvx(7),
                         qlFailed(8),
                         notAvail(9)
                     }
        MAX-ACCESS   read-only
        STATUS       current
        DESCRIPTION  "Main Board / Ctrl Card EXT CLK Quality Level."
        ::= { extClkGroupEntry 8 }

    squelch OBJECT-TYPE
        SYNTAX       INTEGER { normal(1), squelch(2) }
        MAX-ACCESS   read-only
        STATUS       current
        DESCRIPTION  "Main Board / Ctrl Card EXT CLK Squelch Status."
        ::= { extClkGroupEntry 9 }

    clk2mTypeMismatch OBJECT-TYPE
        SYNTAX       SeverityValue
        MAX-ACCESS   read-only
        STATUS       obsolete
        DESCRIPTION  "Main Board / Ctrl Card EXT CLK Type Mismatch Alarm."
        ::= { extClkGroupEntry 10 }

    asFanGroup OBJECT IDENTIFIER
        ::= { alarmStatusGroup 7 }

    fanGroupTable OBJECT-TYPE
        SYNTAX       SEQUENCE OF FanGroupEntry
        MAX-ACCESS   not-accessible
        STATUS       current
        DESCRIPTION  "Represents FAN Card Alarm / Status."
        ::= { asFanGroup 1 }

    fanGroupEntry OBJECT-TYPE
        SYNTAX       FanGroupEntry
        MAX-ACCESS   not-accessible
        STATUS       current
        DESCRIPTION  ""
        INDEX        { fanGroupIndex }
        ::= { fanGroupTable 1 }

    FanGroupEntry ::= SEQUENCE {
        fanGroupIndex      Integer32,
        fanGroupNEAddress  IpAddress,
        fanAlarm           SeverityValue,
        fanUnequipped      SeverityValue
    }

    fanGroupIndex OBJECT-TYPE
        SYNTAX       Integer32
        MAX-ACCESS   not-accessible
        STATUS       current
        DESCRIPTION  "Index of this table."
        ::= { fanGroupEntry 1 }

    fanGroupNEAddress OBJECT-TYPE
        SYNTAX       IpAddress
        MAX-ACCESS   not-accessible
        STATUS       current
        DESCRIPTION  "reserved."
        ::= { fanGroupEntry 2 }

    fanAlarm OBJECT-TYPE
        SYNTAX       SeverityValue
        MAX-ACCESS   read-only
        STATUS       obsolete
        DESCRIPTION  "FAN FAIL Alarm."
        ::= { fanGroupEntry 3 }

    fanUnequipped OBJECT-TYPE
        SYNTAX       SeverityValue
        MAX-ACCESS   read-only
        STATUS       obsolete
        DESCRIPTION  "FAN Unequipped Alarm."
        ::= { fanGroupEntry 4 }

    asPsGroup OBJECT IDENTIFIER
        ::= { alarmStatusGroup 8 }

    psGroupTable OBJECT-TYPE
        SYNTAX       SEQUENCE OF PsGroupEntry
        MAX-ACCESS   not-accessible
        STATUS       current
        DESCRIPTION  
            "Represents Main Board / Ctrl Card Power Supply Alarm / Status."
        ::= { asPsGroup 1 }

    psGroupEntry OBJECT-TYPE
        SYNTAX       PsGroupEntry
        MAX-ACCESS   not-accessible
        STATUS       current
        DESCRIPTION  ""
        INDEX        { psGroupIndex }
        ::= { psGroupTable 1 }

    PsGroupEntry ::= SEQUENCE {
        psGroupIndex      Integer32,
        psGroupNEAddress  IpAddress,
        psPowerSupply     SeverityValue,
        psUnequipped      SeverityValue
    }

    psGroupIndex OBJECT-TYPE
        SYNTAX       Integer32
        MAX-ACCESS   not-accessible
        STATUS       current
        DESCRIPTION  "Index of this table."
        ::= { psGroupEntry 1 }

    psGroupNEAddress OBJECT-TYPE
        SYNTAX       IpAddress
        MAX-ACCESS   not-accessible
        STATUS       current
        DESCRIPTION  "reserved."
        ::= { psGroupEntry 2 }

    psPowerSupply OBJECT-TYPE
        SYNTAX       SeverityValue
        MAX-ACCESS   read-only
        STATUS       current
        DESCRIPTION  "Main Board / Ctrl Card Power Supply Alarm."
        ::= { psGroupEntry 3 }

    psUnequipped OBJECT-TYPE
        SYNTAX       SeverityValue
        MAX-ACCESS   read-only
        STATUS       current
        DESCRIPTION  
            "Main Board / Ctrl Card Power Supply Unequipped Alarm."
        ::= { psGroupEntry 4 }

    asTCNGroup OBJECT IDENTIFIER
        ::= { alarmStatusGroup 9 }

    tcn15minDataRadioGroup OBJECT IDENTIFIER
        ::= { asTCNGroup 1 }

    tcn15minDataRadioTable OBJECT-TYPE
        SYNTAX       SEQUENCE OF Tcn15minDataRadioEntry
        MAX-ACCESS   not-accessible
        STATUS       current
        DESCRIPTION  
            "Represents Threashold Crossing Alarm Status of 15 minutes PMON
            for Radio."
        ::= { tcn15minDataRadioGroup 1 }

    tcn15minDataRadioEntry OBJECT-TYPE
        SYNTAX       Tcn15minDataRadioEntry
        MAX-ACCESS   not-accessible
        STATUS       current
        DESCRIPTION  ""
        INDEX        { tcn15minDataModemIfIndex, tcn15minDataModemMonitorName }
        ::= { tcn15minDataRadioTable 1 }

    Tcn15minDataRadioEntry ::= SEQUENCE {
        tcn15minDataModemIfIndex      InterfaceIndex,
        tcn15minDataModemMonitorName  INTEGER,
        tcn15minDataRadioNEAddress    IpAddress,
        tcn15minDataRf                SeverityValue
    }

    tcn15minDataModemIfIndex OBJECT-TYPE
        SYNTAX       InterfaceIndex
        MAX-ACCESS   not-accessible
        STATUS       current
        DESCRIPTION  
            "Index of this table. Unique number of the radio interface."
        ::= { tcn15minDataRadioEntry 1 }

    tcn15minDataModemMonitorName OBJECT-TYPE
        SYNTAX       INTEGER { bbe(1), es(2), ses(3), sep(4), uas(5), ofs(6) }
        MAX-ACCESS   not-accessible
        STATUS       current
        DESCRIPTION  
            "Index of this table. The index value shows counting item."
        ::= { tcn15minDataRadioEntry 2 }

    tcn15minDataRadioNEAddress OBJECT-TYPE
        SYNTAX       IpAddress
        MAX-ACCESS   not-accessible
        STATUS       current
        DESCRIPTION  "reserved."
        ::= { tcn15minDataRadioEntry 3 }

    tcn15minDataRf OBJECT-TYPE
        SYNTAX       SeverityValue
        MAX-ACCESS   read-only
        STATUS       current
        DESCRIPTION  
            "TCN MODEM 15 minutes RF Monitoring Alarm per counting item."
        ::= { tcn15minDataRadioEntry 4 }

    tcn15minRxLevTable OBJECT-TYPE
        SYNTAX       SEQUENCE OF Tcn15minRxLevEntry
        MAX-ACCESS   not-accessible
        STATUS       current
        DESCRIPTION  
            "Represents Threshold Crossing Alarm Status of 15 minutes Rx
            Level Alarm."
        ::= { tcn15minDataRadioGroup 2 }

    tcn15minRxLevEntry OBJECT-TYPE
        SYNTAX       Tcn15minRxLevEntry
        MAX-ACCESS   not-accessible
        STATUS       current
        DESCRIPTION  ""
        INDEX        { tcn15minRxLevIfIndex }
        ::= { tcn15minRxLevTable 1 }

    Tcn15minRxLevEntry ::= SEQUENCE {
        tcn15minRxLevIfIndex    InterfaceIndex,
        tcn15minRxLevNEAddress  IpAddress,
        tcn15minRxLev           SeverityValue
    }

    tcn15minRxLevIfIndex OBJECT-TYPE
        SYNTAX       InterfaceIndex
        MAX-ACCESS   not-accessible
        STATUS       current
        DESCRIPTION  
            "Index of this table. Unique number of the radio interface."
        ::= { tcn15minRxLevEntry 1 }

    tcn15minRxLevNEAddress OBJECT-TYPE
        SYNTAX       IpAddress
        MAX-ACCESS   not-accessible
        STATUS       current
        DESCRIPTION  "reserved"
        ::= { tcn15minRxLevEntry 2 }

    tcn15minRxLev OBJECT-TYPE
        SYNTAX       SeverityValue
        MAX-ACCESS   read-only
        STATUS       current
        DESCRIPTION  "TCN MODEM 15 minutes RX Level (Min) Alarm."
        ::= { tcn15minRxLevEntry 3 }

    tcn1dayDataRadioGroup OBJECT IDENTIFIER
        ::= { asTCNGroup 3 }

    tcn1dayDataRadioTable OBJECT-TYPE
        SYNTAX       SEQUENCE OF Tcn1dayDataRadioEntry
        MAX-ACCESS   not-accessible
        STATUS       current
        DESCRIPTION  
            "Represents Threashold Crossing Alarm Status of 1 day PMON for
            Radio."
        ::= { tcn1dayDataRadioGroup 1 }

    tcn1dayDataRadioEntry OBJECT-TYPE
        SYNTAX       Tcn1dayDataRadioEntry
        MAX-ACCESS   not-accessible
        STATUS       current
        DESCRIPTION  ""
        INDEX        { tcn1dayDataModemIfIndex, tcn1dayDataModemMonitorName }
        ::= { tcn1dayDataRadioTable 1 }

    Tcn1dayDataRadioEntry ::= SEQUENCE {
        tcn1dayDataModemIfIndex      InterfaceIndex,
        tcn1dayDataModemMonitorName  INTEGER,
        tcn1dayDataRadioNEAddress    IpAddress,
        tcn1dayDataRf                SeverityValue
    }

    tcn1dayDataModemIfIndex OBJECT-TYPE
        SYNTAX       InterfaceIndex
        MAX-ACCESS   not-accessible
        STATUS       current
        DESCRIPTION  
            "Index of this table. Unique number of the radio interface."
        ::= { tcn1dayDataRadioEntry 1 }

    tcn1dayDataModemMonitorName OBJECT-TYPE
        SYNTAX       INTEGER { bbe(1), es(2), ses(3), sep(4), uas(5), ofs(6) }
        MAX-ACCESS   not-accessible
        STATUS       current
        DESCRIPTION  
            "Index of this table. The index value shows counting item."
        ::= { tcn1dayDataRadioEntry 2 }

    tcn1dayDataRadioNEAddress OBJECT-TYPE
        SYNTAX       IpAddress
        MAX-ACCESS   not-accessible
        STATUS       current
        DESCRIPTION  "reserved"
        ::= { tcn1dayDataRadioEntry 3 }

    tcn1dayDataRf OBJECT-TYPE
        SYNTAX       SeverityValue
        MAX-ACCESS   read-only
        STATUS       current
        DESCRIPTION  
            "TCN MODEM 1 day RF Monitoring Alarm per counting item."
        ::= { tcn1dayDataRadioEntry 4 }

    tcn1dayRxLevTable OBJECT-TYPE
        SYNTAX       SEQUENCE OF Tcn1dayRxLevEntry
        MAX-ACCESS   not-accessible
        STATUS       current
        DESCRIPTION  
            "Represents Threshold Crossing Alarm Status of 1 day Rx Level
            Alarm."
        ::= { tcn1dayDataRadioGroup 2 }

    tcn1dayRxLevEntry OBJECT-TYPE
        SYNTAX       Tcn1dayRxLevEntry
        MAX-ACCESS   not-accessible
        STATUS       current
        DESCRIPTION  ""
        INDEX        { tcn1dayRxLevIfIndex }
        ::= { tcn1dayRxLevTable 1 }

    Tcn1dayRxLevEntry ::= SEQUENCE {
        tcn1dayRxLevIfIndex    InterfaceIndex,
        tcn1dayRxLevNEAddress  IpAddress,
        tcn1dayRxLev           SeverityValue
    }

    tcn1dayRxLevIfIndex OBJECT-TYPE
        SYNTAX       InterfaceIndex
        MAX-ACCESS   not-accessible
        STATUS       current
        DESCRIPTION  
            "Index of this table. Unique number of the radio interface."
        ::= { tcn1dayRxLevEntry 1 }

    tcn1dayRxLevNEAddress OBJECT-TYPE
        SYNTAX       IpAddress
        MAX-ACCESS   not-accessible
        STATUS       current
        DESCRIPTION  "reserved"
        ::= { tcn1dayRxLevEntry 2 }

    tcn1dayRxLev OBJECT-TYPE
        SYNTAX       SeverityValue
        MAX-ACCESS   read-only
        STATUS       current
        DESCRIPTION  "TCN MODEM 1 day RX Level (Min) Alarm."
        ::= { tcn1dayRxLevEntry 3 }

    tcn15minDataRmonGroup OBJECT IDENTIFIER
        ::= { asTCNGroup 5 }

    tcn15minDataRmonTable OBJECT-TYPE
        SYNTAX       SEQUENCE OF Tcn15minDataRmonEntry
        MAX-ACCESS   not-accessible
        STATUS       current
        DESCRIPTION  
            "Represents Threshold Crossing Alarm of 15 minutes RMON for
            Ethernet Port."
        ::= { tcn15minDataRmonGroup 1 }

    tcn15minDataRmonEntry OBJECT-TYPE
        SYNTAX       Tcn15minDataRmonEntry
        MAX-ACCESS   not-accessible
        STATUS       current
        DESCRIPTION  ""
        INDEX        { tcn15minRmonIfIndex }
        ::= { tcn15minDataRmonTable 1 }

    Tcn15minDataRmonEntry ::= SEQUENCE {
        tcn15minRmonIfIndex                 InterfaceIndex,
        tcn15minRmonNEAddress               IpAddress,
        tcn15minHCRxEthStatsDropEvents      SeverityValue,
        tcn15minHCRxEthStatsUndersizePkts   SeverityValue,
        tcn15minHCRxEthStatsFragments       SeverityValue,
        tcn15minHCRxEthStatsCRCAlignErrors  SeverityValue,
        tcn15minHCRxEthStatsOversizePkts    SeverityValue,
        tcn15minHCTxEthStatsCollisions      SeverityValue
    }

    tcn15minRmonIfIndex OBJECT-TYPE
        SYNTAX       InterfaceIndex
        MAX-ACCESS   not-accessible
        STATUS       current
        DESCRIPTION  
            "Index of this table. Unique number of the Ethernet Port."
        ::= { tcn15minDataRmonEntry 1 }

    tcn15minRmonNEAddress OBJECT-TYPE
        SYNTAX       IpAddress
        MAX-ACCESS   not-accessible
        STATUS       current
        DESCRIPTION  "reserved"
        ::= { tcn15minDataRmonEntry 2 }

    tcn15minHCRxEthStatsDropEvents OBJECT-TYPE
        SYNTAX       SeverityValue
        MAX-ACCESS   read-only
        STATUS       current
        DESCRIPTION  
            "RMON(Ethernet Port) TCN 15 minutes RX Drop Events Alarm"
        ::= { tcn15minDataRmonEntry 3 }

    tcn15minHCRxEthStatsUndersizePkts OBJECT-TYPE
        SYNTAX       SeverityValue
        MAX-ACCESS   read-only
        STATUS       current
        DESCRIPTION  
            "RMON(Ethernet Port) TCN 15 minutes RX Undersize Packets Alarm."
        ::= { tcn15minDataRmonEntry 4 }

    tcn15minHCRxEthStatsFragments OBJECT-TYPE
        SYNTAX       SeverityValue
        MAX-ACCESS   read-only
        STATUS       current
        DESCRIPTION  
            "RMON(Ethernet Port) TCN 15 minutes RX Fragments Alarm."
        ::= { tcn15minDataRmonEntry 5 }

    tcn15minHCRxEthStatsCRCAlignErrors OBJECT-TYPE
        SYNTAX       SeverityValue
        MAX-ACCESS   read-only
        STATUS       current
        DESCRIPTION  
            "RMON(Ethernet Port) TCN 15 minutes RX CRC Alignment Errors
            Alarm."
        ::= { tcn15minDataRmonEntry 6 }

    tcn15minHCRxEthStatsOversizePkts OBJECT-TYPE
        SYNTAX       SeverityValue
        MAX-ACCESS   read-only
        STATUS       current
        DESCRIPTION  
            "RMON(Ethernet Port) TCN 15 minutes RX Oversize Packets Alarm."
        ::= { tcn15minDataRmonEntry 7 }

    tcn15minHCTxEthStatsCollisions OBJECT-TYPE
        SYNTAX       SeverityValue
        MAX-ACCESS   read-only
        STATUS       current
        DESCRIPTION  
            "RMON(Ethernet Port) TCN 15 minutes TX Collisions Alarm."
        ::= { tcn15minDataRmonEntry 8 }

    tcn1dayDataRmonGroup OBJECT IDENTIFIER
        ::= { asTCNGroup 6 }

    tcn1dayDataRmonTable OBJECT-TYPE
        SYNTAX       SEQUENCE OF Tcn1dayDataRmonEntry
        MAX-ACCESS   not-accessible
        STATUS       current
        DESCRIPTION  
            "Represents Threshold Crossing Alarm of 1 day RMON for Ethernet
            Port"
        ::= { tcn1dayDataRmonGroup 1 }

    tcn1dayDataRmonEntry OBJECT-TYPE
        SYNTAX       Tcn1dayDataRmonEntry
        MAX-ACCESS   not-accessible
        STATUS       current
        DESCRIPTION  ""
        INDEX        { tcn1dayRmonIfIndex }
        ::= { tcn1dayDataRmonTable 1 }

    Tcn1dayDataRmonEntry ::= SEQUENCE {
        tcn1dayRmonIfIndex                 InterfaceIndex,
        tcn1dayRmonNEAddress               IpAddress,
        tcn1dayHCRxEthStatsDropEvents      SeverityValue,
        tcn1dayHCRxEthStatsUndersizePkts   SeverityValue,
        tcn1dayHCRxEthStatsFragments       SeverityValue,
        tcn1dayHCRxEthStatsCRCAlignErrors  SeverityValue,
        tcn1dayHCRxEthStatsOversizePkts    SeverityValue,
        tcn1dayHCTxEthStatsCollisions      SeverityValue
    }

    tcn1dayRmonIfIndex OBJECT-TYPE
        SYNTAX       InterfaceIndex
        MAX-ACCESS   not-accessible
        STATUS       current
        DESCRIPTION  
            "Index of this table. Unique number of the Ethernet Port."
        ::= { tcn1dayDataRmonEntry 1 }

    tcn1dayRmonNEAddress OBJECT-TYPE
        SYNTAX       IpAddress
        MAX-ACCESS   not-accessible
        STATUS       current
        DESCRIPTION  "reserved."
        ::= { tcn1dayDataRmonEntry 2 }

    tcn1dayHCRxEthStatsDropEvents OBJECT-TYPE
        SYNTAX       SeverityValue
        MAX-ACCESS   read-only
        STATUS       current
        DESCRIPTION  "RMON(Ethernet Port) TCN 1 day RX Drop Events Alarm"
        ::= { tcn1dayDataRmonEntry 3 }

    tcn1dayHCRxEthStatsUndersizePkts OBJECT-TYPE
        SYNTAX       SeverityValue
        MAX-ACCESS   read-only
        STATUS       current
        DESCRIPTION  
            "RMON(Ethernet Port) TCN 1 day RX Undersize Packets Alarm."
        ::= { tcn1dayDataRmonEntry 4 }

    tcn1dayHCRxEthStatsFragments OBJECT-TYPE
        SYNTAX       SeverityValue
        MAX-ACCESS   read-only
        STATUS       current
        DESCRIPTION  "RMON(Ethernet Port) TCN 1 day RX Fragments Alarm."
        ::= { tcn1dayDataRmonEntry 5 }

    tcn1dayHCRxEthStatsCRCAlignErrors OBJECT-TYPE
        SYNTAX       SeverityValue
        MAX-ACCESS   read-only
        STATUS       current
        DESCRIPTION  
            "RMON(Ethernet Port) TCN 1 day RX CRC Alignment Errors Alarm."
        ::= { tcn1dayDataRmonEntry 6 }

    tcn1dayHCRxEthStatsOversizePkts OBJECT-TYPE
        SYNTAX       SeverityValue
        MAX-ACCESS   read-only
        STATUS       current
        DESCRIPTION  
            "RMON(Ethernet Port) TCN 1 day RX Oversize Packets Alarm."
        ::= { tcn1dayDataRmonEntry 7 }

    tcn1dayHCTxEthStatsCollisions OBJECT-TYPE
        SYNTAX       SeverityValue
        MAX-ACCESS   read-only
        STATUS       current
        DESCRIPTION  "RMON(Ethernet Port) TCN 1 day TX Collisions Alarm."
        ::= { tcn1dayDataRmonEntry 8 }

    tcn15minDataSfpGroup OBJECT IDENTIFIER
        ::= { asTCNGroup 7 }

    tcn15minSfpTable OBJECT-TYPE
        SYNTAX       SEQUENCE OF Tcn15minSfpEntry
        MAX-ACCESS   not-accessible
        STATUS       current
        DESCRIPTION  
            "Represents Threshold Crossing Alarm Status of 15 minutes ETH
            Port Sfp Tx/Rx Power."
        ::= { tcn15minDataSfpGroup 2 }

    tcn15minSfpEntry OBJECT-TYPE
        SYNTAX       Tcn15minSfpEntry
        MAX-ACCESS   not-accessible
        STATUS       current
        DESCRIPTION  ""
        INDEX        { tcn15minSfpIfIndex }
        ::= { tcn15minSfpTable 1 }

    Tcn15minSfpEntry ::= SEQUENCE {
        tcn15minSfpIfIndex    InterfaceIndex,
        tcn15minSfpNEAddress  IpAddress,
        tcn15minSfpTxPower    SeverityValue,
        tcn15minSfpRxPower    SeverityValue
    }

    tcn15minSfpIfIndex OBJECT-TYPE
        SYNTAX       InterfaceIndex
        MAX-ACCESS   not-accessible
        STATUS       current
        DESCRIPTION  ""
        ::= { tcn15minSfpEntry 1 }

    tcn15minSfpNEAddress OBJECT-TYPE
        SYNTAX       IpAddress
        MAX-ACCESS   not-accessible
        STATUS       current
        DESCRIPTION  "reserved"
        ::= { tcn15minSfpEntry 2 }

    tcn15minSfpTxPower OBJECT-TYPE
        SYNTAX       SeverityValue
        MAX-ACCESS   read-only
        STATUS       current
        DESCRIPTION  "TCN 15 minutes ETH Port Sfp Tx Power(Min)."
        ::= { tcn15minSfpEntry 3 }

    tcn15minSfpRxPower OBJECT-TYPE
        SYNTAX       SeverityValue
        MAX-ACCESS   read-only
        STATUS       current
        DESCRIPTION  "TCN 15 minutes ETH Port Sfp Rx Power(Min)."
        ::= { tcn15minSfpEntry 4 }

    tcn1dayDataSfpGroup OBJECT IDENTIFIER
        ::= { asTCNGroup 8 }

    tcn1daySfpTable OBJECT-TYPE
        SYNTAX       SEQUENCE OF Tcn1daySfpEntry
        MAX-ACCESS   not-accessible
        STATUS       current
        DESCRIPTION  
            "Represents Threshold Crossing Alarm Status of 1 day ETH Port Sfp
            Tx/Rx Power."
        ::= { tcn1dayDataSfpGroup 2 }

    tcn1daySfpEntry OBJECT-TYPE
        SYNTAX       Tcn1daySfpEntry
        MAX-ACCESS   not-accessible
        STATUS       current
        DESCRIPTION  ""
        INDEX        { tcn1daySfpIfIndex }
        ::= { tcn1daySfpTable 1 }

    Tcn1daySfpEntry ::= SEQUENCE {
        tcn1daySfpIfIndex    InterfaceIndex,
        tcn1daySfpNEAddress  IpAddress,
        tcn1daySfpTxPower    SeverityValue,
        tcn1daySfpRxPower    SeverityValue
    }

    tcn1daySfpIfIndex OBJECT-TYPE
        SYNTAX       InterfaceIndex
        MAX-ACCESS   not-accessible
        STATUS       current
        DESCRIPTION  ""
        ::= { tcn1daySfpEntry 1 }

    tcn1daySfpNEAddress OBJECT-TYPE
        SYNTAX       IpAddress
        MAX-ACCESS   not-accessible
        STATUS       current
        DESCRIPTION  "reserved"
        ::= { tcn1daySfpEntry 2 }

    tcn1daySfpTxPower OBJECT-TYPE
        SYNTAX       SeverityValue
        MAX-ACCESS   read-only
        STATUS       current
        DESCRIPTION  "TCN 1 day ETH Port Sfp Tx Power(Min)."
        ::= { tcn1daySfpEntry 3 }

    tcn1daySfpRxPower OBJECT-TYPE
        SYNTAX       SeverityValue
        MAX-ACCESS   read-only
        STATUS       current
        DESCRIPTION  "TCN 1 day ETH Port Sfp Rx Power(Min)."
        ::= { tcn1daySfpEntry 4 }

    asETHGroup OBJECT IDENTIFIER
        ::= { alarmStatusGroup 13 }

    asRstpGroup OBJECT IDENTIFIER
        ::= { asETHGroup 2 }

    asRstpBridgeTable OBJECT-TYPE
        SYNTAX       SEQUENCE OF AsRstpBridgeEntry
        MAX-ACCESS   not-accessible
        STATUS       current
        DESCRIPTION  "Alarm / Status information of RSTP."
        ::= { asRstpGroup 1 }

    asRstpBridgeEntry OBJECT-TYPE
        SYNTAX       AsRstpBridgeEntry
        MAX-ACCESS   not-accessible
        STATUS       current
        DESCRIPTION  ""
        INDEX        { asRstpBridgeIndex }
        ::= { asRstpBridgeTable 1 }

    AsRstpBridgeEntry ::= SEQUENCE {
        asRstpBridgeIndex           Integer32,
        asRstpBridgeNEAddress       IpAddress,
        asRstpBridgeDesignatedRoot  BridgeId,
        asRstpBridgeTopChanges      Integer32
    }

    asRstpBridgeIndex OBJECT-TYPE
        SYNTAX       Integer32 (1..1)
        MAX-ACCESS   not-accessible
        STATUS       current
        DESCRIPTION  "Index of this table."
        ::= { asRstpBridgeEntry 1 }

    asRstpBridgeNEAddress OBJECT-TYPE
        SYNTAX       IpAddress
        MAX-ACCESS   not-accessible
        STATUS       current
        DESCRIPTION  "reserved."
        ::= { asRstpBridgeEntry 2 }

    asRstpBridgeDesignatedRoot OBJECT-TYPE
        SYNTAX       BridgeId
        MAX-ACCESS   read-only
        STATUS       current
        DESCRIPTION  
            "The bridge identifier of the root of the spanning tree."
        ::= { asRstpBridgeEntry 3 }

    asRstpBridgeTopChanges OBJECT-TYPE
        SYNTAX       Integer32
        MAX-ACCESS   read-only
        STATUS       current
        DESCRIPTION  
            "RSTP Topology Changed Status. The total number of topology
            chagnes detected by this bridge since the equipment was last
            initialized."
        ::= { asRstpBridgeEntry 4 }

    asRstpPortTable OBJECT-TYPE
        SYNTAX       SEQUENCE OF AsRstpPortEntry
        MAX-ACCESS   not-accessible
        STATUS       current
        DESCRIPTION  
            "Alarm / Status information of RSTP per Ethernet Port."
        ::= { asRstpGroup 2 }

    asRstpPortEntry OBJECT-TYPE
        SYNTAX       AsRstpPortEntry
        MAX-ACCESS   not-accessible
        STATUS       current
        DESCRIPTION  ""
        INDEX        { asRstpIfIndex }
        ::= { asRstpPortTable 1 }

    AsRstpPortEntry ::= SEQUENCE {
        asRstpIfIndex                                  InterfaceIndex,
        asRstpPortNEAddress                            IpAddress,
        asRstpPortRole                                 INTEGER,
        asRstpPortState                                INTEGER,
        asRstpPortNewRootBridgeDetectedBridgePriority  BridgeId,
        asRstpPortProtocolMigrationVersion             INTEGER,
        asRstpPortPathCost                             Integer32,
        asRstpPortInvalidBpduCause                     INTEGER,
        asRstpPortDesignatedCost                       Integer32,
        asRstpPortDesignatedBridge                     BridgeId,
        asRstpPortDesignatedPort                       OCTET STRING,
        asRstpPortForwardTransitions                   Counter32,
        asRstpPortOperEdgePort                         INTEGER,
        asRstpPortOperPointToPoint                     EnableDisableValue
    }

    asRstpIfIndex OBJECT-TYPE
        SYNTAX       InterfaceIndex
        MAX-ACCESS   not-accessible
        STATUS       current
        DESCRIPTION  "Index of this table."
        ::= { asRstpPortEntry 1 }

    asRstpPortNEAddress OBJECT-TYPE
        SYNTAX       IpAddress
        MAX-ACCESS   not-accessible
        STATUS       current
        DESCRIPTION  "reserved"
        ::= { asRstpPortEntry 2 }

    asRstpPortRole OBJECT-TYPE
        SYNTAX       INTEGER {
                         disabledPort(1),
                         alternatePort(2),
                         backupPort(3),
                         rootPort(4),
                         designatedPort(5)
                     }
        MAX-ACCESS   read-only
        STATUS       current
        DESCRIPTION  
            "RSTP Port Role. The port's current state, as defined by
            application of the Spanning Tree Protocol. This state controls
            what action a port takes on reception of a frame."
        ::= { asRstpPortEntry 3 }

    asRstpPortState OBJECT-TYPE
        SYNTAX       INTEGER {
                         disabled(1),
                         blocking(2),
                         listening(3),
                         learning(4),
                         forwarding(5),
                         broken(6),
                         discarding(7)
                     }
        MAX-ACCESS   read-only
        STATUS       current
        DESCRIPTION  
            "RSTP Port Status. The port's current state, as defined by
            application of the Spanning Tree Protocol. This state controls
            what action a port takes on reception of a frame."
        ::= { asRstpPortEntry 4 }

    asRstpPortNewRootBridgeDetectedBridgePriority OBJECT-TYPE
        SYNTAX       BridgeId
        MAX-ACCESS   read-only
        STATUS       current
        DESCRIPTION  
            "RSTP New Bridge Detect Status. The unique Bridge Identifier of
            the Bridge recorded as the Root in the Configuration BPDUs."
        ::= { asRstpPortEntry 5 }

    asRstpPortProtocolMigrationVersion OBJECT-TYPE
        SYNTAX       INTEGER { stp(1), rstp(2) }
        MAX-ACCESS   read-only
        STATUS       current
        DESCRIPTION  
            "RSTP Protocol Migration. The port's operating protocol version."
        ::= { asRstpPortEntry 6 }

    asRstpPortPathCost OBJECT-TYPE
        SYNTAX       Integer32 (1..200000000)
        MAX-ACCESS   read-only
        STATUS       current
        DESCRIPTION  
            "The port's path cost, defined by application depends on its port
            speed."
        ::= { asRstpPortEntry 7 }

    asRstpPortInvalidBpduCause OBJECT-TYPE
        SYNTAX       INTEGER {
                         restore(0),
                         protocolID(1),
                         bpduType(2),
                         tcnLength(3),
                         rstpLength(4),
                         configLength(5),
                         maxAge(6),
                         fwdDelay(7),
                         helloTime(8)
                     }
        MAX-ACCESS   read-only
        STATUS       current
        DESCRIPTION  
            "RSTP Invalid BPDU Received. The event status of invalid BPDU
            received."
        ::= { asRstpPortEntry 8 }

    asRstpPortDesignatedCost OBJECT-TYPE
        SYNTAX       Integer32 (1..200000000)
        MAX-ACCESS   read-only
        STATUS       current
        DESCRIPTION  
            "The path cost of the Designated Port of the segment connected to
            this port."
        ::= { asRstpPortEntry 9 }

    asRstpPortDesignatedBridge OBJECT-TYPE
        SYNTAX       BridgeId
        MAX-ACCESS   read-only
        STATUS       current
        DESCRIPTION  
            "The bridge identifier of the bridge that this port considers to
            be the designated Bridge for this port's segment."
        ::= { asRstpPortEntry 10 }

    asRstpPortDesignatedPort OBJECT-TYPE
        SYNTAX       OCTET STRING
        MAX-ACCESS   read-only
        STATUS       current
        DESCRIPTION  
            "The port identifier of the port on the designated bridge for
            this port's segment."
        ::= { asRstpPortEntry 11 }

    asRstpPortForwardTransitions OBJECT-TYPE
        SYNTAX       Counter32
        MAX-ACCESS   read-only
        STATUS       current
        DESCRIPTION  
            "The number of times this port has transitioned from the learning
            state to the forwarding state."
        ::= { asRstpPortEntry 12 }

    asRstpPortOperEdgePort OBJECT-TYPE
        SYNTAX       INTEGER { alarmOff(0), alarmOn(1) }
        MAX-ACCESS   read-only
        STATUS       current
        DESCRIPTION  
            "The operational value of the edge port parameter. This object is
            initialized to 'alarmOff'. This object will be changed to
            'alarmOn' on reception of a BPDU if the corresponding
            'provRstpExtPortAdminEdgePort' is set to 'enabled'."
        ::= { asRstpPortEntry 13 }

    asRstpPortOperPointToPoint OBJECT-TYPE
        SYNTAX       EnableDisableValue
        MAX-ACCESS   read-only
        STATUS       current
        DESCRIPTION  
            "The operational value of the point-to-point port parameter."
        ::= { asRstpPortEntry 14 }

    asEthOamGroup OBJECT IDENTIFIER
        ::= { asETHGroup 3 }

    asEthOamCcGroup OBJECT IDENTIFIER
        ::= { asEthOamGroup 1 }

    asEthOamMepCcmFaultTable OBJECT-TYPE
        SYNTAX       SEQUENCE OF AsEthOamMepCcmFaultEntry
        MAX-ACCESS   not-accessible
        STATUS       current
        DESCRIPTION  "ETH-CC Fault Management Table"
        ::= { asEthOamCcGroup 1 }

    asEthOamMepCcmFaultEntry OBJECT-TYPE
        SYNTAX       AsEthOamMepCcmFaultEntry
        MAX-ACCESS   not-accessible
        STATUS       current
        DESCRIPTION  ""
        INDEX        { asEthOamMepCcmIndex }
        ::= { asEthOamMepCcmFaultTable 1 }

    AsEthOamMepCcmFaultEntry ::= SEQUENCE {
        asEthOamMepCcmIndex                   IpeMepId,
        asEthOamMepCcmFaultNEAddress          IpAddress,
        asEthOamMepCcmLOC                     SeverityValue,
        asEthOamMepCcmRdiReceived             SeverityValue,
        asEthOamMepCcmMismergeCondition       SeverityValue,
        asEthOamMepCcmUnexpectedMepCondition  SeverityValue
    }

    asEthOamMepCcmIndex OBJECT-TYPE
        SYNTAX       IpeMepId
        MAX-ACCESS   not-accessible
        STATUS       current
        DESCRIPTION  
            "Index of this table. The value is not same as MEP ID of protocol
            sense, uniquely assigned administrative value."
        ::= { asEthOamMepCcmFaultEntry 1 }

    asEthOamMepCcmFaultNEAddress OBJECT-TYPE
        SYNTAX       IpAddress
        MAX-ACCESS   not-accessible
        STATUS       current
        DESCRIPTION  "reserved"
        ::= { asEthOamMepCcmFaultEntry 2 }

    asEthOamMepCcmLOC OBJECT-TYPE
        SYNTAX       SeverityValue
        MAX-ACCESS   read-only
        STATUS       current
        DESCRIPTION  
            "ETH-OAM LOC Alarm. The MEP is not receiveing valid CCM from at
            least one of the remote MEP."
        ::= { asEthOamMepCcmFaultEntry 3 }

    asEthOamMepCcmRdiReceived OBJECT-TYPE
        SYNTAX       SeverityValue
        MAX-ACCESS   read-only
        STATUS       current
        DESCRIPTION  
            "ETH-OAM RDI Alarm. A remote MEP is reported the RDI in is last
            CCM."
        ::= { asEthOamMepCcmFaultEntry 4 }

    asEthOamMepCcmMismergeCondition OBJECT-TYPE
        SYNTAX       SeverityValue
        MAX-ACCESS   read-only
        STATUS       obsolete
        DESCRIPTION  "obsoleted"
        ::= { asEthOamMepCcmFaultEntry 5 }

    asEthOamMepCcmUnexpectedMepCondition OBJECT-TYPE
        SYNTAX       SeverityValue
        MAX-ACCESS   read-only
        STATUS       obsolete
        DESCRIPTION  "obsoleted"
        ::= { asEthOamMepCcmFaultEntry 6 }

    asEthOamMepCcmDbTable OBJECT-TYPE
        SYNTAX       SEQUENCE OF AsEthOamMepCcmDbEntry
        MAX-ACCESS   not-accessible
        STATUS       current
        DESCRIPTION  "ETH-CCM Database Table"
        ::= { asEthOamCcGroup 2 }

    asEthOamMepCcmDbEntry OBJECT-TYPE
        SYNTAX       AsEthOamMepCcmDbEntry
        MAX-ACCESS   not-accessible
        STATUS       current
        DESCRIPTION  ""
        INDEX        { asEthOamMepCcmDbPeerMepIndex }
        ::= { asEthOamMepCcmDbTable 1 }

    AsEthOamMepCcmDbEntry ::= SEQUENCE {
        asEthOamMepCcmDbPeerMepIndex  IpeMepId,
        asEthOamMepCcmDbNEAddress     IpAddress,
        asEthOamMepCcmDbMepIndex      IpeMepId,
        asEthOamMepCcmDbPeerMepId     Integer32,
        asEthOamMepCcmDbMepId         Integer32,
        asEthOamMepCcmDbCondition     TruthValue,
        asEthOamMepCcmDbRdiReceived   TruthValue
    }

    asEthOamMepCcmDbPeerMepIndex OBJECT-TYPE
        SYNTAX       IpeMepId
        MAX-ACCESS   not-accessible
        STATUS       current
        DESCRIPTION  
            "Index of this table representing peer MEP index. The value is
            not same as MEP ID of protocol sense, uniquely assigned
            administrative value."
        ::= { asEthOamMepCcmDbEntry 1 }

    asEthOamMepCcmDbNEAddress OBJECT-TYPE
        SYNTAX       IpAddress
        MAX-ACCESS   not-accessible
        STATUS       current
        DESCRIPTION  "reserved"
        ::= { asEthOamMepCcmDbEntry 2 }

    asEthOamMepCcmDbMepIndex OBJECT-TYPE
        SYNTAX       IpeMepId
        MAX-ACCESS   read-only
        STATUS       current
        DESCRIPTION  "Administrative Mep Index of own MEP."
        ::= { asEthOamMepCcmDbEntry 3 }

    asEthOamMepCcmDbPeerMepId OBJECT-TYPE
        SYNTAX       Integer32 (0..8191)
        MAX-ACCESS   read-only
        STATUS       current
        DESCRIPTION  
            "this object represents protocol sense MEP ID of peer MEP."
        ::= { asEthOamMepCcmDbEntry 4 }

    asEthOamMepCcmDbMepId OBJECT-TYPE
        SYNTAX       Integer32 (0..8191)
        MAX-ACCESS   read-only
        STATUS       current
        DESCRIPTION  
            "this object represents protocol sense MEP ID of local MEP."
        ::= { asEthOamMepCcmDbEntry 5 }

    asEthOamMepCcmDbCondition OBJECT-TYPE
        SYNTAX       TruthValue
        MAX-ACCESS   read-only
        STATUS       current
        DESCRIPTION  
            "This object represents the status of LOC detection per Peer
            MEP."
        ::= { asEthOamMepCcmDbEntry 6 }

    asEthOamMepCcmDbRdiReceived OBJECT-TYPE
        SYNTAX       TruthValue
        MAX-ACCESS   read-only
        STATUS       current
        DESCRIPTION  
            "This object represents the status of RDI receive status per peer
            MEP."
        ::= { asEthOamMepCcmDbEntry 7 }

    asEthOamMegCcmFaultTable OBJECT-TYPE
        SYNTAX       SEQUENCE OF AsEthOamMegCcmFaultEntry
        MAX-ACCESS   not-accessible
        STATUS       current
        DESCRIPTION  "ETH-CC Fault Management Table(MEG)"
        ::= { asEthOamCcGroup 3 }

    asEthOamMegCcmFaultEntry OBJECT-TYPE
        SYNTAX       AsEthOamMegCcmFaultEntry
        MAX-ACCESS   not-accessible
        STATUS       current
        DESCRIPTION  ""
        INDEX        { asEthOamMegCcmIndex }
        ::= { asEthOamMegCcmFaultTable 1 }

    AsEthOamMegCcmFaultEntry ::= SEQUENCE {
        asEthOamMegCcmIndex                   Integer32,
        asEthOamMegCcmFaultNEAddress          IpAddress,
        asEthOamMegCcmMismergeCondition       SeverityValue,
        asEthOamMegCcmUnexpectedMepCondition  SeverityValue
    }

    asEthOamMegCcmIndex OBJECT-TYPE
        SYNTAX       Integer32 (1..128)
        MAX-ACCESS   not-accessible
        STATUS       current
        DESCRIPTION  "Index of this table."
        ::= { asEthOamMegCcmFaultEntry 1 }

    asEthOamMegCcmFaultNEAddress OBJECT-TYPE
        SYNTAX       IpAddress
        MAX-ACCESS   not-accessible
        STATUS       current
        DESCRIPTION  "reserved."
        ::= { asEthOamMegCcmFaultEntry 2 }

    asEthOamMegCcmMismergeCondition OBJECT-TYPE
        SYNTAX       SeverityValue
        MAX-ACCESS   read-only
        STATUS       current
        DESCRIPTION  
            "ETH-OAM Mismerge Alarm. The MEP received a CCM frame with
            correct MEG level but an incorrect MEG ID (Maintenance Domain
            Name)."
        ::= { asEthOamMegCcmFaultEntry 3 }

    asEthOamMegCcmUnexpectedMepCondition OBJECT-TYPE
        SYNTAX       SeverityValue
        MAX-ACCESS   read-only
        STATUS       current
        DESCRIPTION  
            "ETH-OAM Unexpected MEP Alarm. The MEP Received a CCM frame with
            the correct MEG level and MEG ID, but unexpected MEP ID."
        ::= { asEthOamMegCcmFaultEntry 4 }

    asEthOamAisGroup OBJECT IDENTIFIER
        ::= { asEthOamGroup 2 }

    asEthOamAisTable OBJECT-TYPE
        SYNTAX       SEQUENCE OF AsEthOamAisEntry
        MAX-ACCESS   not-accessible
        STATUS       obsolete
        DESCRIPTION  "ETH-AIS Status Table"
        ::= { asEthOamAisGroup 1 }

    asEthOamAisEntry OBJECT-TYPE
        SYNTAX       AsEthOamAisEntry
        MAX-ACCESS   not-accessible
        STATUS       obsolete
        DESCRIPTION  ""
        INDEX        { asEthOamAisMepIndex }
        ::= { asEthOamAisTable 1 }

    AsEthOamAisEntry ::= SEQUENCE {
        asEthOamAisMepIndex   IpeMepId,
        asEthOamAisNEAddress  IpAddress,
        asEthOamAisCondition  SeverityValue,
        asEthOamAisPeriod     INTEGER
    }

    asEthOamAisMepIndex OBJECT-TYPE
        SYNTAX       IpeMepId
        MAX-ACCESS   not-accessible
        STATUS       obsolete
        DESCRIPTION  "Index of this table. Administrative ID of local MEP."
        ::= { asEthOamAisEntry 1 }

    asEthOamAisNEAddress OBJECT-TYPE
        SYNTAX       IpAddress
        MAX-ACCESS   not-accessible
        STATUS       obsolete
        DESCRIPTION  "reserved"
        ::= { asEthOamAisEntry 2 }

    asEthOamAisCondition OBJECT-TYPE
        SYNTAX       SeverityValue
        MAX-ACCESS   read-only
        STATUS       obsolete
        DESCRIPTION  "obsoleted"
        ::= { asEthOamAisEntry 3 }

    asEthOamAisPeriod OBJECT-TYPE
        SYNTAX       INTEGER { invalid(0), period-1s(4), period-1min(6) }
        MAX-ACCESS   read-only
        STATUS       obsolete
        DESCRIPTION  "obsoleted"
        ::= { asEthOamAisEntry 4 }

    asEthOamBnGroup OBJECT IDENTIFIER
        ::= { asEthOamGroup 3 }

    asEthOamBnmTransmissionInfoTable OBJECT-TYPE
        SYNTAX       SEQUENCE OF AsEthOamBnmTransmissionInfoEntry
        MAX-ACCESS   not-accessible
        STATUS       current
        DESCRIPTION  
            "ETH-BN, Bandwidth Notification, Transmission Information Table."
        ::= { asEthOamBnGroup 1 }

    asEthOamBnmTransmissionInfoEntry OBJECT-TYPE
        SYNTAX       AsEthOamBnmTransmissionInfoEntry
        MAX-ACCESS   not-accessible
        STATUS       current
        DESCRIPTION  ""
        INDEX        { asEthOamBnmTransmissionIndex }
        ::= { asEthOamBnmTransmissionInfoTable 1 }

    AsEthOamBnmTransmissionInfoEntry ::= SEQUENCE {
        asEthOamBnmTransmissionIndex         IpeMepId,
        asEthOamBnmTransmissionNEAddress     IpAddress,
        asEthOamBnmTransmissionNominalValue  Integer32,
        asEthOamBnmTransmissionCurrentValue  Integer32
    }

    asEthOamBnmTransmissionIndex OBJECT-TYPE
        SYNTAX       IpeMepId
        MAX-ACCESS   not-accessible
        STATUS       current
        DESCRIPTION  "Index of this table."
        ::= { asEthOamBnmTransmissionInfoEntry 1 }

    asEthOamBnmTransmissionNEAddress OBJECT-TYPE
        SYNTAX       IpAddress
        MAX-ACCESS   not-accessible
        STATUS       current
        DESCRIPTION  "reserved"
        ::= { asEthOamBnmTransmissionInfoEntry 2 }

    asEthOamBnmTransmissionNominalValue OBJECT-TYPE
        SYNTAX       Integer32 (0..10312)
        UNITS        "Mbps"
        MAX-ACCESS   read-only
        STATUS       current
        DESCRIPTION  
            "This object represents nominal value of the radio bandwidth
            information of Server MEP.  The units of this value is Mbps."
        ::= { asEthOamBnmTransmissionInfoEntry 3 }

    asEthOamBnmTransmissionCurrentValue OBJECT-TYPE
        SYNTAX       Integer32 (0..10312)
        UNITS        "Mbps"
        MAX-ACCESS   read-only
        STATUS       current
        DESCRIPTION  
            "This object represents current value of the radio bandwidth
            information of Server MEP.  The units of this value is Mbps."
        ::= { asEthOamBnmTransmissionInfoEntry 4 }

    asEthOamBnmReceptionInfoTable OBJECT-TYPE
        SYNTAX       SEQUENCE OF AsEthOamBnmReceptionInfoEntry
        MAX-ACCESS   not-accessible
        STATUS       current
        DESCRIPTION  
            "ETH-BN, Bandwidth Notification, Reception Information Table."
        ::= { asEthOamBnGroup 2 }

    asEthOamBnmReceptionInfoEntry OBJECT-TYPE
        SYNTAX       AsEthOamBnmReceptionInfoEntry
        MAX-ACCESS   not-accessible
        STATUS       current
        DESCRIPTION  
            "ETH-BN, Bandwidth Notification, Reception Information Entry."
        INDEX        { asEthOamBnmReceptionIndex }
        ::= { asEthOamBnmReceptionInfoTable 1 }

    AsEthOamBnmReceptionInfoEntry ::= SEQUENCE {
        asEthOamBnmReceptionIndex         IpeMepId,
        asEthOamBnmReceptionNEAddress     IpAddress,
        asEthOamBnmReceptionPeriod        INTEGER,
        asEthOamBnmReceptionCurrentValue  Integer32,
        asEthOamBnmReceptionUNP           SeverityValue,
        asEthOamBnmReceptionLOC           SeverityValue,
        asEthOamBnmReceptionUNL           SeverityValue
    }

    asEthOamBnmReceptionIndex OBJECT-TYPE
        SYNTAX       IpeMepId
        MAX-ACCESS   not-accessible
        STATUS       current
        DESCRIPTION  "Index of this table."
        ::= { asEthOamBnmReceptionInfoEntry 1 }

    asEthOamBnmReceptionNEAddress OBJECT-TYPE
        SYNTAX       IpAddress
        MAX-ACCESS   not-accessible
        STATUS       current
        DESCRIPTION  "reserved"
        ::= { asEthOamBnmReceptionInfoEntry 2 }

    asEthOamBnmReceptionPeriod OBJECT-TYPE
        SYNTAX       INTEGER {
                         invalid(0),
                         period-1s(1),
                         period-10s(2),
                         period-1min(3)
                     }
        MAX-ACCESS   read-only
        STATUS       obsolete
        DESCRIPTION  "BNM Frame Transmition Period"
        ::= { asEthOamBnmReceptionInfoEntry 3 }

    asEthOamBnmReceptionCurrentValue OBJECT-TYPE
        SYNTAX       Integer32 (0..10312)
        MAX-ACCESS   read-only
        STATUS       current
        DESCRIPTION  
            "This object represents current value of the radio bandwidth
            information of Client MEP.  The unit of this value is Mbps."
        ::= { asEthOamBnmReceptionInfoEntry 4 }

    asEthOamBnmReceptionUNP OBJECT-TYPE
        SYNTAX       SeverityValue
        MAX-ACCESS   read-only
        STATUS       current
        DESCRIPTION  "ETH-BN UNP Alarm"
        ::= { asEthOamBnmReceptionInfoEntry 5 }

    asEthOamBnmReceptionLOC OBJECT-TYPE
        SYNTAX       SeverityValue
        MAX-ACCESS   read-only
        STATUS       current
        DESCRIPTION  "ETH-BN LOC Alarm"
        ::= { asEthOamBnmReceptionInfoEntry 6 }

    asEthOamBnmReceptionUNL OBJECT-TYPE
        SYNTAX       SeverityValue
        MAX-ACCESS   read-only
        STATUS       current
        DESCRIPTION  "ETH-BN UNL Alarm"
        ::= { asEthOamBnmReceptionInfoEntry 7 }

    asFdbGroup OBJECT IDENTIFIER
        ::= { asETHGroup 6 }

    asFdbEquipmentTable OBJECT-TYPE
        SYNTAX       SEQUENCE OF AsFdbEquipmentEntry
        MAX-ACCESS   not-accessible
        STATUS       current
        DESCRIPTION  "Forwarding Database Status per Equipment."
        ::= { asFdbGroup 1 }

    asFdbEquipmentEntry OBJECT-TYPE
        SYNTAX       AsFdbEquipmentEntry
        MAX-ACCESS   not-accessible
        STATUS       current
        DESCRIPTION  ""
        INDEX        { asFdbEquipmentIndex }
        ::= { asFdbEquipmentTable 1 }

    AsFdbEquipmentEntry ::= SEQUENCE {
        asFdbEquipmentIndex              Integer32,
        asFdbEquipmentNEAddress          IpAddress,
        asFdbEquipmentLearningCount      Gauge32,
        asFdbEquipmentLearningLimitOver  INTEGER
    }

    asFdbEquipmentIndex OBJECT-TYPE
        SYNTAX       Integer32 (1..1)
        MAX-ACCESS   not-accessible
        STATUS       current
        DESCRIPTION  
            "Index of this table. This object is created per equipment."
        ::= { asFdbEquipmentEntry 1 }

    asFdbEquipmentNEAddress OBJECT-TYPE
        SYNTAX       IpAddress
        MAX-ACCESS   not-accessible
        STATUS       current
        DESCRIPTION  "reserved."
        ::= { asFdbEquipmentEntry 2 }

    asFdbEquipmentLearningCount OBJECT-TYPE
        SYNTAX       Gauge32
        MAX-ACCESS   read-only
        STATUS       current
        DESCRIPTION  
            "Total FDB Dynamic Entry Count. the number of forwarding entries
            which is learned currently."
        ::= { asFdbEquipmentEntry 3 }

    asFdbEquipmentLearningLimitOver OBJECT-TYPE
        SYNTAX       INTEGER { notReached(1), reached(2) }
        MAX-ACCESS   read-only
        STATUS       current
        DESCRIPTION  
            "Total FDB Full. learning limit status. When
            'asFdbEquipmentLearningCount' reaches
            'provFdbEquipmentNumberOfLearningEntry', this object will be
            changed to 'reached'."
        ::= { asFdbEquipmentEntry 4 }

    asFdbPortTable OBJECT-TYPE
        SYNTAX       SEQUENCE OF AsFdbPortEntry
        MAX-ACCESS   not-accessible
        STATUS       current
        DESCRIPTION  ""
        ::= { asFdbGroup 2 }

    asFdbPortEntry OBJECT-TYPE
        SYNTAX       AsFdbPortEntry
        MAX-ACCESS   not-accessible
        STATUS       current
        DESCRIPTION  "Forwarding Database Status per port."
        INDEX        { asFdbPortIfIndex }
        ::= { asFdbPortTable 1 }

    AsFdbPortEntry ::= SEQUENCE {
        asFdbPortIfIndex            InterfaceIndex,
        asFdbPortNEAddress          IpAddress,
        asFdbPortLearningCount      Gauge32,
        asFdbPortLearningLimitOver  INTEGER
    }

    asFdbPortIfIndex OBJECT-TYPE
        SYNTAX       InterfaceIndex
        MAX-ACCESS   not-accessible
        STATUS       current
        DESCRIPTION  "Index of this table."
        ::= { asFdbPortEntry 1 }

    asFdbPortNEAddress OBJECT-TYPE
        SYNTAX       IpAddress
        MAX-ACCESS   not-accessible
        STATUS       current
        DESCRIPTION  "reserved."
        ::= { asFdbPortEntry 2 }

    asFdbPortLearningCount OBJECT-TYPE
        SYNTAX       Gauge32
        MAX-ACCESS   read-only
        STATUS       current
        DESCRIPTION  
            "FDB Dynamic Entry Count. The number of forwarding entries which
            is learned currently."
        ::= { asFdbPortEntry 3 }

    asFdbPortLearningLimitOver OBJECT-TYPE
        SYNTAX       INTEGER { notReached(1), reached(2) }
        MAX-ACCESS   read-only
        STATUS       current
        DESCRIPTION  
            "FDB Full. learning limit status. When 'asFdbPortLearningCount'
            reaches corresponding 'provFdbPortLearningLimit', this object
            will be changed to 'reached'."
        ::= { asFdbPortEntry 4 }

    asFdbVlanTable OBJECT-TYPE
        SYNTAX       SEQUENCE OF AsFdbVlanEntry
        MAX-ACCESS   not-accessible
        STATUS       current
        DESCRIPTION  "Forwarding Database status per VLAN."
        ::= { asFdbGroup 3 }

    asFdbVlanEntry OBJECT-TYPE
        SYNTAX       AsFdbVlanEntry
        MAX-ACCESS   not-accessible
        STATUS       current
        DESCRIPTION  ""
        INDEX        { asFdbVlanIndex }
        ::= { asFdbVlanTable 1 }

    AsFdbVlanEntry ::= SEQUENCE {
        asFdbVlanIndex              Integer32,
        asFdbVlanNEAddress          IpAddress,
        asFdbVlanLearningCount      Gauge32,
        asFdbVlanLearningLimitOver  INTEGER
    }

    asFdbVlanIndex OBJECT-TYPE
        SYNTAX       Integer32 (1..4094)
        MAX-ACCESS   not-accessible
        STATUS       current
        DESCRIPTION  "Index of this table. The value is same as VLAN ID."
        ::= { asFdbVlanEntry 1 }

    asFdbVlanNEAddress OBJECT-TYPE
        SYNTAX       IpAddress
        MAX-ACCESS   not-accessible
        STATUS       current
        DESCRIPTION  "reserved."
        ::= { asFdbVlanEntry 2 }

    asFdbVlanLearningCount OBJECT-TYPE
        SYNTAX       Gauge32
        MAX-ACCESS   read-only
        STATUS       current
        DESCRIPTION  
            "FDB Dynamic Entry Count per VLAN. The number of forwarding
            entries which is learned currently."
        ::= { asFdbVlanEntry 3 }

    asFdbVlanLearningLimitOver OBJECT-TYPE
        SYNTAX       INTEGER { notReached(1), reached(2) }
        MAX-ACCESS   read-only
        STATUS       current
        DESCRIPTION  
            "FDB Full Per VLAN. Learning limit status. When
            'asFdbVlanLearningCount' reaches corresponding
            'provFdbVlanNumberOfLearningEntry', this object will be changed
            to 'reached'."
        ::= { asFdbVlanEntry 4 }

    asLlfGroup OBJECT IDENTIFIER
        ::= { asETHGroup 7 }

    asLlfGroupTable OBJECT-TYPE
        SYNTAX       SEQUENCE OF AsLlfGroupEntry
        MAX-ACCESS   not-accessible
        STATUS       current
        DESCRIPTION  "Link Loss Forwarding(LLF) Status per LLF Group."
        ::= { asLlfGroup 1 }

    asLlfGroupEntry OBJECT-TYPE
        SYNTAX       AsLlfGroupEntry
        MAX-ACCESS   not-accessible
        STATUS       current
        DESCRIPTION  ""
        INDEX        { asLlfGroupIndex }
        ::= { asLlfGroupTable 1 }

    AsLlfGroupEntry ::= SEQUENCE {
        asLlfGroupIndex       Integer32,
        asLlfGroupNEAddress   IpAddress,
        asLlfGroupForceClose  INTEGER,
        asLlfGroupTimeout     INTEGER
    }

    asLlfGroupIndex OBJECT-TYPE
        SYNTAX       Integer32 (1..16)
        MAX-ACCESS   not-accessible
        STATUS       current
        DESCRIPTION  
            "Index of this table. The value means LLF Group Index."
        ::= { asLlfGroupEntry 1 }

    asLlfGroupNEAddress OBJECT-TYPE
        SYNTAX       IpAddress
        MAX-ACCESS   not-accessible
        STATUS       current
        DESCRIPTION  "reserved."
        ::= { asLlfGroupEntry 2 }

    asLlfGroupForceClose OBJECT-TYPE
        SYNTAX       INTEGER { not-forceclose(1), forceclose(2) }
        MAX-ACCESS   read-only
        STATUS       current
        DESCRIPTION  
            "LLF close status. 'forceclose' means that edge port which is
            assigned to the LLF group is closed because of LLF."
        ::= { asLlfGroupEntry 3 }

    asLlfGroupTimeout OBJECT-TYPE
        SYNTAX       INTEGER { received(1), timeout(2) }
        MAX-ACCESS   read-only
        STATUS       current
        DESCRIPTION  
            "LLF Timeout Status. The periodic LLF messages is not received."
        ::= { asLlfGroupEntry 4 }

    asLlfReceiveInfoTable OBJECT-TYPE
        SYNTAX       SEQUENCE OF AsLlfReceiveInfoEntry
        MAX-ACCESS   not-accessible
        STATUS       obsolete
        DESCRIPTION  "Link Loss Forwarding (LLF) Status per port."
        ::= { asLlfGroup 2 }

    asLlfReceiveInfoEntry OBJECT-TYPE
        SYNTAX       AsLlfReceiveInfoEntry
        MAX-ACCESS   not-accessible
        STATUS       obsolete
        DESCRIPTION  ""
        INDEX        { asLlfReceiveInfoIfIndex, asLlfReceiveInfoGroupIndex }
        ::= { asLlfReceiveInfoTable 1 }

    AsLlfReceiveInfoEntry ::= SEQUENCE {
        asLlfReceiveInfoIfIndex     InterfaceIndex,
        asLlfReceiveInfoGroupIndex  Integer32,
        asLlfReceiveInfoNEAddress   IpAddress,
        asLlfReceiveInfoLinkSts     INTEGER
    }

    asLlfReceiveInfoIfIndex OBJECT-TYPE
        SYNTAX       InterfaceIndex
        MAX-ACCESS   not-accessible
        STATUS       obsolete
        DESCRIPTION  "reserved."
        ::= { asLlfReceiveInfoEntry 1 }

    asLlfReceiveInfoGroupIndex OBJECT-TYPE
        SYNTAX       Integer32 (1..16)
        MAX-ACCESS   not-accessible
        STATUS       obsolete
        DESCRIPTION  
            "LLF Group Index. The value means LLF Group Index which is
            assigned to the port."
        ::= { asLlfReceiveInfoEntry 2 }

    asLlfReceiveInfoNEAddress OBJECT-TYPE
        SYNTAX       IpAddress
        MAX-ACCESS   not-accessible
        STATUS       obsolete
        DESCRIPTION  "reserved"
        ::= { asLlfReceiveInfoEntry 3 }

    asLlfReceiveInfoLinkSts OBJECT-TYPE
        SYNTAX       INTEGER { down(1), up(2) }
        MAX-ACCESS   read-only
        STATUS       obsolete
        DESCRIPTION  "LLF Link Information which is received from peer."
        ::= { asLlfReceiveInfoEntry 4 }

    asETHPortGroup OBJECT IDENTIFIER
        ::= { asETHGroup 8 }

    asETHPortTable OBJECT-TYPE
        SYNTAX       SEQUENCE OF AsETHPortEntry
        MAX-ACCESS   not-accessible
        STATUS       current
        DESCRIPTION  "Ethernet Port Status Table."
        ::= { asETHPortGroup 1 }

    asETHPortEntry OBJECT-TYPE
        SYNTAX       AsETHPortEntry
        MAX-ACCESS   not-accessible
        STATUS       current
        DESCRIPTION  ""
        INDEX        { asETHPortIfIndex }
        ::= { asETHPortTable 1 }

    AsETHPortEntry ::= SEQUENCE {
        asETHPortIfIndex              InterfaceIndex,
        asETHPortNEAddress            IpAddress,
        asETHPortInterfaceType        INTEGER,
        asETHPortSpeedDuplex          INTEGER,
        asETHPortFlowControl          INTEGER,
        asETHPortMDIMDIX              INTEGER,
        asETHPortLinkStatus           SeverityValue,
        asETHPortAdminStatus          INTEGER,
        asETHPortSFPEquip             SeverityValue,
        asETHPortSFPLos               SeverityValue,
        asETHPortSFPTxError           SeverityValue,
        asETHPortSFPTypeMismatch      SeverityValue,
        asETHPortOperStatus           INTEGER,
        asETHPortLlfOamReceived       INTEGER,
        asETHPortAlsStatus            OffOnValue,
        asETHPortLaserShutdownStatus  OffOnValue,
        asETHPortLocalFault           SeverityValue,
        asETHPortRemoteFault          SeverityValue
    }

    asETHPortIfIndex OBJECT-TYPE
        SYNTAX       InterfaceIndex
        MAX-ACCESS   not-accessible
        STATUS       current
        DESCRIPTION  
            "Index of this table. The administrative number which is assigned
            to the port uniquely."
        ::= { asETHPortEntry 1 }

    asETHPortNEAddress OBJECT-TYPE
        SYNTAX       IpAddress
        MAX-ACCESS   not-accessible
        STATUS       current
        DESCRIPTION  "reserved"
        ::= { asETHPortEntry 2 }

    asETHPortInterfaceType OBJECT-TYPE
        SYNTAX       INTEGER { invalid(0), fiber(1), copper(2) }
        MAX-ACCESS   read-only
        STATUS       current
        DESCRIPTION  
            "GbE SFP Port Type Status. This object represents interface type
            which is installed currently."
        ::= { asETHPortEntry 3 }

    asETHPortSpeedDuplex OBJECT-TYPE
        SYNTAX       INTEGER {
                         invalid(0),
                         s10M-HALF(1),
                         s10M-FULL(2),
                         s100M-HALF(3),
                         s100M-FULL(4),
                         s1000M-FULL(5),
                         s10G-FULL(6),
                         s25G-FULL(7)
                     }
        MAX-ACCESS   read-only
        STATUS       current
        DESCRIPTION  "GbE Speed & Duplex Status."
        ::= { asETHPortEntry 4 }

    asETHPortFlowControl OBJECT-TYPE
        SYNTAX       INTEGER { disable(1), enable(2) }
        MAX-ACCESS   read-only
        STATUS       current
        DESCRIPTION  "GbE Flow Control Status."
        ::= { asETHPortEntry 5 }

    asETHPortMDIMDIX OBJECT-TYPE
        SYNTAX       INTEGER { invalid(0), mdi(1), mdi-x(2) }
        MAX-ACCESS   read-only
        STATUS       current
        DESCRIPTION  "GbE MDI / MDI-X Status."
        ::= { asETHPortEntry 6 }

    asETHPortLinkStatus OBJECT-TYPE
        SYNTAX       SeverityValue
        MAX-ACCESS   read-only
        STATUS       current
        DESCRIPTION  "GbE LAN Link Alarm."
        ::= { asETHPortEntry 7 }

    asETHPortAdminStatus OBJECT-TYPE
        SYNTAX       INTEGER { normal(1), force(2), oamSend(3) }
        MAX-ACCESS   read-only
        STATUS       current
        DESCRIPTION  
            "GbE LLF Status. When the port is closed by LLF, the object will
            be changed to 'force'.
            But if 'provLlfPortMode' is configured to 'edgeOamSend', this
            object will be changed to 'oamSend' when the port is controlled
            by LLF."
        ::= { asETHPortEntry 8 }

    asETHPortSFPEquip OBJECT-TYPE
        SYNTAX       SeverityValue
        MAX-ACCESS   read-only
        STATUS       current
        DESCRIPTION  "GbE SFP Removed Alarm."
        ::= { asETHPortEntry 9 }

    asETHPortSFPLos OBJECT-TYPE
        SYNTAX       SeverityValue
        MAX-ACCESS   read-only
        STATUS       current
        DESCRIPTION  "GbE ETH LOS Alarm."
        ::= { asETHPortEntry 10 }

    asETHPortSFPTxError OBJECT-TYPE
        SYNTAX       SeverityValue
        MAX-ACCESS   read-only
        STATUS       current
        DESCRIPTION  "GbE ETH TF (Transmit FAIL) Alarm."
        ::= { asETHPortEntry 11 }

    asETHPortSFPTypeMismatch OBJECT-TYPE
        SYNTAX       SeverityValue
        MAX-ACCESS   read-only
        STATUS       current
        DESCRIPTION  
            "GbE SFP Type Mismatch Alarm. This object reports that the
            provisioned interface type and the installed media type are
            inconsistent."
        ::= { asETHPortEntry 12 }

    asETHPortOperStatus OBJECT-TYPE
        SYNTAX       INTEGER { invalid(0), linkDown(1), linkUp(2) }
        MAX-ACCESS   read-only
        STATUS       current
        DESCRIPTION  
            "GbE ETH LAN Link Status. This object is not suppressed by the
            lower layer alarms."
        ::= { asETHPortEntry 13 }

    asETHPortLlfOamReceived OBJECT-TYPE
        SYNTAX       INTEGER { invalid(0), normal(1), receive(2) }
        MAX-ACCESS   read-only
        STATUS       current
        DESCRIPTION  
            "GbE LLF message receive status.
            When the port received LLF request messages, the object will
            return the value 'receive'."
        ::= { asETHPortEntry 14 }

    asETHPortAlsStatus OBJECT-TYPE
        SYNTAX       OffOnValue
        MAX-ACCESS   read-only
        STATUS       current
        DESCRIPTION  "ALS Status"
        ::= { asETHPortEntry 15 }

    asETHPortLaserShutdownStatus OBJECT-TYPE
        SYNTAX       OffOnValue
        MAX-ACCESS   read-only
        STATUS       current
        DESCRIPTION  "Laser Shutdown status."
        ::= { asETHPortEntry 16 }

    asETHPortLocalFault OBJECT-TYPE
        SYNTAX       SeverityValue
        MAX-ACCESS   read-only
        STATUS       current
        DESCRIPTION  "XGbE Local Fault"
        ::= { asETHPortEntry 17 }

    asETHPortRemoteFault OBJECT-TYPE
        SYNTAX       SeverityValue
        MAX-ACCESS   read-only
        STATUS       current
        DESCRIPTION  "XGbe Remote Fault"
        ::= { asETHPortEntry 18 }

    asSyncETHGroup OBJECT IDENTIFIER
        ::= { asETHGroup 9 }

    asSyncETHTable OBJECT-TYPE
        SYNTAX       SEQUENCE OF AsSyncETHEntry
        MAX-ACCESS   not-accessible
        STATUS       current
        DESCRIPTION  "Sync Ethernet Status table."
        ::= { asSyncETHGroup 2 }

    asSyncETHEntry OBJECT-TYPE
        SYNTAX       AsSyncETHEntry
        MAX-ACCESS   not-accessible
        STATUS       current
        DESCRIPTION  ""
        INDEX        { asSyncETHIfIndex }
        ::= { asSyncETHTable 1 }

    AsSyncETHEntry ::= SEQUENCE {
        asSyncETHIfIndex     InterfaceIndex,
        asSyncETHNEAddress   IpAddress,
        asSyncETHPortCLKSts  Integer32
    }

    asSyncETHIfIndex OBJECT-TYPE
        SYNTAX       InterfaceIndex
        MAX-ACCESS   read-only
        STATUS       current
        DESCRIPTION  "Index of this table."
        ::= { asSyncETHEntry 1 }

    asSyncETHNEAddress OBJECT-TYPE
        SYNTAX       IpAddress
        MAX-ACCESS   read-only
        STATUS       current
        DESCRIPTION  "reserved."
        ::= { asSyncETHEntry 2 }

    asSyncETHPortCLKSts OBJECT-TYPE
        SYNTAX       Integer32
        MAX-ACCESS   read-only
        STATUS       current
        DESCRIPTION  "Sync ETH Port CLK Status."
        ::= { asSyncETHEntry 3 }

    asQosGroup OBJECT IDENTIFIER
        ::= { asETHGroup 10 }

    asQosTable OBJECT-TYPE
        SYNTAX       SEQUENCE OF AsQosEntry
        MAX-ACCESS   not-accessible
        STATUS       obsolete
        DESCRIPTION  "Qos Information per port."
        ::= { asQosGroup 1 }

    asQosEntry OBJECT-TYPE
        SYNTAX       AsQosEntry
        MAX-ACCESS   not-accessible
        STATUS       obsolete
        DESCRIPTION  ""
        INDEX        { asQosPortindex }
        ::= { asQosTable 1 }

    AsQosEntry ::= SEQUENCE {
        asQosPortindex     InterfaceIndex,
        asQosNEAddress     IpAddress,
        asQosAmrBandWidth  Integer32
    }

    asQosPortindex OBJECT-TYPE
        SYNTAX       InterfaceIndex
        MAX-ACCESS   not-accessible
        STATUS       obsolete
        DESCRIPTION  "Index of this table."
        ::= { asQosEntry 1 }

    asQosNEAddress OBJECT-TYPE
        SYNTAX       IpAddress
        MAX-ACCESS   not-accessible
        STATUS       obsolete
        DESCRIPTION  "reserved."
        ::= { asQosEntry 2 }

    asQosAmrBandWidth OBJECT-TYPE
        SYNTAX       Integer32
        MAX-ACCESS   read-only
        STATUS       obsolete
        DESCRIPTION  
            "The value of Qos bandwidth which is  determined by the smaller
            value of the followings.
             AMR bandwidth - E1 bandwidth - total EIR bandwidth.
              Or
             AMR bandwidth - E1 bandwidth - total CIR bandwidth."
        ::= { asQosEntry 3 }

    asCommonGroup OBJECT IDENTIFIER
        ::= { alarmStatusGroup 14 }

    iduCommonTable OBJECT-TYPE
        SYNTAX       SEQUENCE OF IduCommonEntry
        MAX-ACCESS   not-accessible
        STATUS       current
        DESCRIPTION  "Equipment Configuration Status Table."
        ::= { asCommonGroup 1 }

    iduCommonEntry OBJECT-TYPE
        SYNTAX       IduCommonEntry
        MAX-ACCESS   not-accessible
        STATUS       current
        DESCRIPTION  ""
        INDEX        { iduCommonIndex }
        ::= { iduCommonTable 1 }

    IduCommonEntry ::= SEQUENCE {
        iduCommonIndex      INTEGER,
        iduCommonNEAddress  IpAddress,
        equipConfigStatus   Integer32
    }

    iduCommonIndex OBJECT-TYPE
        SYNTAX       INTEGER { iduCommon(1) }
        MAX-ACCESS   not-accessible
        STATUS       current
        DESCRIPTION  "Index of this table."
        ::= { iduCommonEntry 1 }

    iduCommonNEAddress OBJECT-TYPE
        SYNTAX       IpAddress
        MAX-ACCESS   not-accessible
        STATUS       current
        DESCRIPTION  "reseved"
        ::= { iduCommonEntry 2 }

    equipConfigStatus OBJECT-TYPE
        SYNTAX       Integer32
        MAX-ACCESS   read-only
        STATUS       current
        DESCRIPTION  
            "Equipment Configuration Status. The object is used for
            determining the status synchronization method for the manager
            entity."
        ::= { iduCommonEntry 3 }

    asCommonTable OBJECT-TYPE
        SYNTAX       SEQUENCE OF AsCommonEntry
        MAX-ACCESS   not-accessible
        STATUS       current
        DESCRIPTION  "Installed Card Status table."
        ::= { asCommonGroup 2 }

    asCommonEntry OBJECT-TYPE
        SYNTAX       AsCommonEntry
        MAX-ACCESS   not-accessible
        STATUS       current
        DESCRIPTION  ""
        INDEX        { asCommonIndex }
        ::= { asCommonTable 1 }

    AsCommonEntry ::= SEQUENCE {
        asCommonIndex      Integer32,
        asCommonNEAddress  IpAddress,
        asUserInterface    INTEGER
    }

    asCommonIndex OBJECT-TYPE
        SYNTAX       Integer32
        MAX-ACCESS   not-accessible
        STATUS       current
        DESCRIPTION  
            "Index of this table. The value is equivalent to the slot number
            + 1."
        ::= { asCommonEntry 1 }

    asCommonNEAddress OBJECT-TYPE
        SYNTAX       IpAddress
        MAX-ACCESS   not-accessible
        STATUS       current
        DESCRIPTION  "reserved."
        ::= { asCommonEntry 2 }

    asUserInterface OBJECT-TYPE
        SYNTAX       INTEGER {
                         invalid(0),
                         notUsed(1),
                         ps(14),
                         main(17),
                         modemEX10(38),
                         unknown(99)
                     }
        MAX-ACCESS   read-only
        STATUS       current
        DESCRIPTION  
            "Installed card type.
            The value modemEX10(38) is available only for the iPASOLINK EX
            Advanced."
        ::= { asCommonEntry 3 }

    asCurrentAlarmGroup OBJECT IDENTIFIER
        ::= { alarmStatusGroup 20 }

    asCurrentAlarmTable OBJECT-TYPE
        SYNTAX       SEQUENCE OF AsCurrentAlarmEntry
        MAX-ACCESS   not-accessible
        STATUS       current
        DESCRIPTION  "Current Alarm Table."
        ::= { asCurrentAlarmGroup 1 }

    asCurrentAlarmEntry OBJECT-TYPE
        SYNTAX       AsCurrentAlarmEntry
        MAX-ACCESS   not-accessible
        STATUS       current
        DESCRIPTION  ""
        INDEX        { asCurrentAlarmIndex }
        ::= { asCurrentAlarmTable 1 }

    AsCurrentAlarmEntry ::= SEQUENCE {
        asCurrentAlarmIndex        OBJECT IDENTIFIER,
        asCurrentAlarmNEAddress    IpAddress,
        asCurrentAlarmSeverity     SeverityValue,
        asCurrentAlarmTime         DateAndTime,
        asCurrentAlarmType         AlarmTypeValue,
        asCurrentAlarmName         DisplayString,
        asCurrentAlarmDescription  DisplayString
    }

    asCurrentAlarmIndex OBJECT-TYPE
        SYNTAX       OBJECT IDENTIFIER
        MAX-ACCESS   not-accessible
        STATUS       current
        DESCRIPTION  
            "The OBJECT IDENTIFIER of the object which raised the alarm."
        ::= { asCurrentAlarmEntry 1 }

    asCurrentAlarmNEAddress OBJECT-TYPE
        SYNTAX       IpAddress
        MAX-ACCESS   not-accessible
        STATUS       current
        DESCRIPTION  "reserved."
        ::= { asCurrentAlarmEntry 2 }

    asCurrentAlarmSeverity OBJECT-TYPE
        SYNTAX       SeverityValue
        MAX-ACCESS   read-only
        STATUS       current
        DESCRIPTION  "Alarm severity value."
        ::= { asCurrentAlarmEntry 3 }

    asCurrentAlarmTime OBJECT-TYPE
        SYNTAX       DateAndTime
        MAX-ACCESS   read-only
        STATUS       current
        DESCRIPTION  "The local date and time when the alarm occurred."
        ::= { asCurrentAlarmEntry 4 }

    asCurrentAlarmType OBJECT-TYPE
        SYNTAX       AlarmTypeValue
        MAX-ACCESS   read-only
        STATUS       current
        DESCRIPTION  "Alarm Type."
        ::= { asCurrentAlarmEntry 5 }

    asCurrentAlarmName OBJECT-TYPE
        SYNTAX       DisplayString (SIZE(0..50))
        MAX-ACCESS   read-only
        STATUS       current
        DESCRIPTION  "Alarm Name."
        ::= { asCurrentAlarmEntry 6 }

    asCurrentAlarmDescription OBJECT-TYPE
        SYNTAX       DisplayString (SIZE(0..192))
        MAX-ACCESS   read-only
        STATUS       current
        DESCRIPTION  "Alarm Description."
        ::= { asCurrentAlarmEntry 7 }

    asLicenseGroup OBJECT IDENTIFIER
        ::= { alarmStatusGroup 45 }

    asLicenseAlarmTable OBJECT-TYPE
        SYNTAX       SEQUENCE OF AsLicenseAlarmEntry
        MAX-ACCESS   not-accessible
        STATUS       current
        DESCRIPTION  "License Alarm Table."
        ::= { asLicenseGroup 1 }

    asLicenseAlarmEntry OBJECT-TYPE
        SYNTAX       AsLicenseAlarmEntry
        MAX-ACCESS   not-accessible
        STATUS       current
        DESCRIPTION  ""
        INDEX        { asLicenseAlarmIndex }
        ::= { asLicenseAlarmTable 1 }

    AsLicenseAlarmEntry ::= SEQUENCE {
        asLicenseAlarmIndex      Integer32,
        asLicenseAlarmNEAddress  IpAddress,
        asLicenseAlarm           SeverityValue
    }

    asLicenseAlarmIndex OBJECT-TYPE
        SYNTAX       Integer32 (1..1)
        MAX-ACCESS   not-accessible
        STATUS       current
        DESCRIPTION  "Index of this table."
        ::= { asLicenseAlarmEntry 1 }

    asLicenseAlarmNEAddress OBJECT-TYPE
        SYNTAX       IpAddress
        MAX-ACCESS   not-accessible
        STATUS       current
        DESCRIPTION  "reserved."
        ::= { asLicenseAlarmEntry 2 }

    asLicenseAlarm OBJECT-TYPE
        SYNTAX       SeverityValue
        MAX-ACCESS   read-only
        STATUS       current
        DESCRIPTION  
            "License Alarm.
            The alarm will be asserted when the configuration and install
            license are mismatch. The following operations can be trigger the
            alarm.
              - license downgrade
              - multiple chassis configuration (2U XPIC)
            The alarm will be cleared when the conditions mentioned above are
            cleared."
        ::= { asLicenseAlarmEntry 3 }

    asServiceSwitchGroup OBJECT IDENTIFIER
        ::= { alarmStatusGroup 52 }

    asServiceSwitchTable OBJECT-TYPE
        SYNTAX       SEQUENCE OF AsServiceSwitchEntry
        MAX-ACCESS   not-accessible
        STATUS       current
        DESCRIPTION  "Service Switch Table"
        ::= { asServiceSwitchGroup 1 }

    asServiceSwitchEntry OBJECT-TYPE
        SYNTAX       AsServiceSwitchEntry
        MAX-ACCESS   not-accessible
        STATUS       current
        DESCRIPTION  "Service Switch Entry"
        INDEX        { asServiceSwitchIndex }
        ::= { asServiceSwitchTable 1 }

    AsServiceSwitchEntry ::= SEQUENCE {
        asServiceSwitchIndex        Integer32,
        asServiceSwitchNEAddress    IpAddress,
        asServiceSwitchCurrentPath  INTEGER
    }

    asServiceSwitchIndex OBJECT-TYPE
        SYNTAX       Integer32 (1..64)
        MAX-ACCESS   not-accessible
        STATUS       current
        DESCRIPTION  "Index of this table"
        ::= { asServiceSwitchEntry 1 }

    asServiceSwitchNEAddress OBJECT-TYPE
        SYNTAX       IpAddress
        MAX-ACCESS   not-accessible
        STATUS       current
        DESCRIPTION  "reserved"
        ::= { asServiceSwitchEntry 2 }

    asServiceSwitchCurrentPath OBJECT-TYPE
        SYNTAX       INTEGER {
                         invalid(0),
                         primary(1),
                         secondary(2),
                         notSwitched(3),
                         primaryForced(4),
                         secondaryForced(5)
                     }
        MAX-ACCESS   read-only
        STATUS       current
        DESCRIPTION  "Current Path"
        ::= { asServiceSwitchEntry 3 }

    asTransparentGroup OBJECT IDENTIFIER
        ::= { alarmStatusGroup 62 }

    asTransparentFwdingModeTable OBJECT-TYPE
        SYNTAX       SEQUENCE OF AsTransparentFwdingModeEntry
        MAX-ACCESS   not-accessible
        STATUS       current
        DESCRIPTION  "Forwarding Mode Table."
        ::= { asTransparentGroup 1 }

    asTransparentFwdingModeEntry OBJECT-TYPE
        SYNTAX       AsTransparentFwdingModeEntry
        MAX-ACCESS   not-accessible
        STATUS       current
        DESCRIPTION  ""
        INDEX        { asTransparentFwdingModeIndex }
        ::= { asTransparentFwdingModeTable 1 }

    AsTransparentFwdingModeEntry ::= SEQUENCE {
        asTransparentFwdingModeIndex      Integer32,
        asTransparentFwdingModeNEAddress  IpAddress,
        asTransparentFwdingModeMismatch   SeverityValue
    }

    asTransparentFwdingModeIndex OBJECT-TYPE
        SYNTAX       Integer32 (1..1)
        MAX-ACCESS   not-accessible
        STATUS       current
        DESCRIPTION  "Index of this table."
        ::= { asTransparentFwdingModeEntry 1 }

    asTransparentFwdingModeNEAddress OBJECT-TYPE
        SYNTAX       IpAddress
        MAX-ACCESS   not-accessible
        STATUS       current
        DESCRIPTION  "reserved."
        ::= { asTransparentFwdingModeEntry 2 }

    asTransparentFwdingModeMismatch OBJECT-TYPE
        SYNTAX       SeverityValue
        MAX-ACCESS   read-only
        STATUS       current
        DESCRIPTION  
            "This object indicates the Forwarding Mode Setting Mismatch alarm
            for Transparent Mode."
        ::= { asTransparentFwdingModeEntry 3 }

-----------------------------------------------
-- inventoryGroup Definitions
-----------------------------------------------

    invCardInfoGroup OBJECT IDENTIFIER
        ::= { inventoryGroup 1 }

    invMainInfoTable OBJECT-TYPE
        SYNTAX       SEQUENCE OF InvMainInfoEntry
        MAX-ACCESS   not-accessible
        STATUS       current
        DESCRIPTION  
            "Equipment Inventory Information (IDU) - Main Board / Ctrl Card"
        ::= { invCardInfoGroup 1 }

    invMainInfoEntry OBJECT-TYPE
        SYNTAX       InvMainInfoEntry
        MAX-ACCESS   not-accessible
        STATUS       current
        DESCRIPTION  ""
        INDEX        { invMainInfoIndex }
        ::= { invMainInfoTable 1 }

    InvMainInfoEntry ::= SEQUENCE {
        invMainInfoIndex             Integer32,
        invMainInfoNEAddress         IpAddress,
        invMainName                  DisplayString,
        invMainCodeNo                DisplayString,
        invMainSerialNo              DisplayString,
        invMainManufacturedDate      DisplayString,
        invMainFirmVersion           DisplayString,
        invMainFirmVersionUncurrent  DisplayString,
        invMainCardHardVersion       DisplayString
    }

    invMainInfoIndex OBJECT-TYPE
        SYNTAX       Integer32 (1..1|17..18)
        MAX-ACCESS   not-accessible
        STATUS       current
        DESCRIPTION  
            "Index of this table. value range: 17 (VR 1/VR 2/VR 4), 17-18
            (1000/VR 10), 1 (others)"
        ::= { invMainInfoEntry 1 }

    invMainInfoNEAddress OBJECT-TYPE
        SYNTAX       IpAddress
        MAX-ACCESS   not-accessible
        STATUS       current
        DESCRIPTION  "reserved."
        ::= { invMainInfoEntry 2 }

    invMainName OBJECT-TYPE
        SYNTAX       DisplayString
        MAX-ACCESS   read-only
        STATUS       current
        DESCRIPTION  "Main Board / Ctrl Card Name."
        ::= { invMainInfoEntry 3 }

    invMainCodeNo OBJECT-TYPE
        SYNTAX       DisplayString
        MAX-ACCESS   read-only
        STATUS       current
        DESCRIPTION  "Main Board / Ctrl Card Code No."
        ::= { invMainInfoEntry 4 }

    invMainSerialNo OBJECT-TYPE
        SYNTAX       DisplayString (SIZE(1..8))
        MAX-ACCESS   read-write
        STATUS       current
        DESCRIPTION  "Main Board / Ctrl Card Serial No."
        ::= { invMainInfoEntry 5 }

    invMainManufacturedDate OBJECT-TYPE
        SYNTAX       DisplayString
        MAX-ACCESS   read-only
        STATUS       current
        DESCRIPTION  "Main Board / Ctrl Card Manufactured Date"
        ::= { invMainInfoEntry 6 }

    invMainFirmVersion OBJECT-TYPE
        SYNTAX       DisplayString
        MAX-ACCESS   read-only
        STATUS       current
        DESCRIPTION  "Main Board / Ctrl Card Firmware Version."
        ::= { invMainInfoEntry 7 }

    invMainFirmVersionUncurrent OBJECT-TYPE
        SYNTAX       DisplayString
        MAX-ACCESS   read-only
        STATUS       current
        DESCRIPTION  "Main Board / Ctrl Card Firmware Version (Uncurrent)."
        ::= { invMainInfoEntry 8 }

    invMainCardHardVersion OBJECT-TYPE
        SYNTAX       DisplayString
        MAX-ACCESS   read-only
        STATUS       current
        DESCRIPTION  "Main Board / Ctrl Card Hardware Version."
        ::= { invMainInfoEntry 9 }

    invCardInfoTable OBJECT-TYPE
        SYNTAX       SEQUENCE OF InvCardInfoEntry
        MAX-ACCESS   not-accessible
        STATUS       current
        DESCRIPTION  
            "Equipment Inventory Information (IDU) - Option / Universal Card"
        ::= { invCardInfoGroup 2 }

    invCardInfoEntry OBJECT-TYPE
        SYNTAX       InvCardInfoEntry
        MAX-ACCESS   not-accessible
        STATUS       current
        DESCRIPTION  ""
        INDEX        { invCardInfoIndex }
        ::= { invCardInfoTable 1 }

    InvCardInfoEntry ::= SEQUENCE {
        invCardInfoIndex             Integer32,
        invCardInfoNEAddress         IpAddress,
        invCardName                  DisplayString,
        invCardCodeNo                DisplayString,
        invCardSerialNo              DisplayString,
        invCardManufacturedDate      DisplayString,
        invCardFirmVersion           DisplayString,
        invCardHardVersion           DisplayString,
        invCardFirmVersionUncurrent  DisplayString
    }

    invCardInfoIndex OBJECT-TYPE
        SYNTAX       Integer32
        MAX-ACCESS   not-accessible
        STATUS       current
        DESCRIPTION  "Index of this table."
        ::= { invCardInfoEntry 1 }

    invCardInfoNEAddress OBJECT-TYPE
        SYNTAX       IpAddress
        MAX-ACCESS   not-accessible
        STATUS       current
        DESCRIPTION  "reserved"
        ::= { invCardInfoEntry 2 }

    invCardName OBJECT-TYPE
        SYNTAX       DisplayString
        MAX-ACCESS   read-only
        STATUS       current
        DESCRIPTION  
            "Card Name. when the card is removed, the value will be changed
            to '**'."
        ::= { invCardInfoEntry 3 }

    invCardCodeNo OBJECT-TYPE
        SYNTAX       DisplayString
        MAX-ACCESS   read-only
        STATUS       current
        DESCRIPTION  
            "Card Code No. when the card is removed, the value will be
            changed to '**'."
        ::= { invCardInfoEntry 4 }

    invCardSerialNo OBJECT-TYPE
        SYNTAX       DisplayString
        MAX-ACCESS   read-only
        STATUS       current
        DESCRIPTION  
            "Card Serial No. when the card is removed, the value will be
            changed to '**'."
        ::= { invCardInfoEntry 5 }

    invCardManufacturedDate OBJECT-TYPE
        SYNTAX       DisplayString
        MAX-ACCESS   read-only
        STATUS       current
        DESCRIPTION  
            "Card Manufactured Date. when the card is removed, the value will
            be changed to '**'."
        ::= { invCardInfoEntry 6 }

    invCardFirmVersion OBJECT-TYPE
        SYNTAX       DisplayString
        MAX-ACCESS   read-only
        STATUS       obsolete
        DESCRIPTION  
            "Card Firmware Version. when the card is removed, the value will
            be changed to '**'."
        ::= { invCardInfoEntry 7 }

    invCardHardVersion OBJECT-TYPE
        SYNTAX       DisplayString
        MAX-ACCESS   read-only
        STATUS       obsolete
        DESCRIPTION  
            "Card Hardware Version. when the card is removed, the value will
            be changed to '**'."
        ::= { invCardInfoEntry 8 }

    invCardFirmVersionUncurrent OBJECT-TYPE
        SYNTAX       DisplayString
        MAX-ACCESS   read-only
        STATUS       obsolete
        DESCRIPTION  
            "Card Firmware Version (uncurrent side). When the card is
            removed, the value will be changed to '**'."
        ::= { invCardInfoEntry 9 }

    invFPGAInfoTable OBJECT-TYPE
        SYNTAX       SEQUENCE OF InvFPGAInfoEntry
        MAX-ACCESS   not-accessible
        STATUS       current
        DESCRIPTION  "Equipment Inventory Information (IDU) - FPGA"
        ::= { inventoryGroup 2 }

    invFPGAInfoEntry OBJECT-TYPE
        SYNTAX       InvFPGAInfoEntry
        MAX-ACCESS   not-accessible
        STATUS       obsolete
        DESCRIPTION  ""
        INDEX        { invFPGAInfoIndex }
        ::= { invFPGAInfoTable 1 }

    InvFPGAInfoEntry ::= SEQUENCE {
        invFPGAInfoIndex      Integer32,
        invFPGAInfoNEAddress  IpAddress,
        invFPGAName           DisplayString,
        invFPGACodeNo         DisplayString,
        invFPGAHardVersion    DisplayString
    }

    invFPGAInfoIndex OBJECT-TYPE
        SYNTAX       Integer32
        MAX-ACCESS   not-accessible
        STATUS       current
        DESCRIPTION  "Index of this table."
        ::= { invFPGAInfoEntry 1 }

    invFPGAInfoNEAddress OBJECT-TYPE
        SYNTAX       IpAddress
        MAX-ACCESS   not-accessible
        STATUS       current
        DESCRIPTION  "reserved."
        ::= { invFPGAInfoEntry 2 }

    invFPGAName OBJECT-TYPE
        SYNTAX       DisplayString
        MAX-ACCESS   read-only
        STATUS       current
        DESCRIPTION  
            "FPGA Name. when the card is removed, the value will be changed
            to '**'."
        ::= { invFPGAInfoEntry 3 }

    invFPGACodeNo OBJECT-TYPE
        SYNTAX       DisplayString
        MAX-ACCESS   read-only
        STATUS       current
        DESCRIPTION  
            "FPGA Code No. when the card is removed, the value will be
            changed to '**'."
        ::= { invFPGAInfoEntry 4 }

    invFPGAHardVersion OBJECT-TYPE
        SYNTAX       DisplayString
        MAX-ACCESS   read-only
        STATUS       current
        DESCRIPTION  
            "FPGA Version. when the card is removed, the value will be
            changed to '**'."
        ::= { invFPGAInfoEntry 5 }

    invModuleInfoOduTable OBJECT-TYPE
        SYNTAX       SEQUENCE OF InvModuleInfoOduEntry
        MAX-ACCESS   not-accessible
        STATUS       current
        DESCRIPTION  "Equipment Inventory Information (ODU)"
        ::= { inventoryGroup 3 }

    invModuleInfoOduEntry OBJECT-TYPE
        SYNTAX       InvModuleInfoOduEntry
        MAX-ACCESS   not-accessible
        STATUS       current
        DESCRIPTION  ""
        INDEX        { invModuleInfoOduIfIndex }
        ::= { invModuleInfoOduTable 1 }

    InvModuleInfoOduEntry ::= SEQUENCE {
        invModuleInfoOduIfIndex          InterfaceIndex,
        invModuleInfoOduNEAddress        IpAddress,
        invOduCardName                   DisplayString,
        invOduCardCodeNo                 DisplayString,
        invOduCardHardVersion            DisplayString,
        invOduCardSerialNo               DisplayString,
        invOduCardManufacturedDate       DisplayString,
        invOduCardFirmCurrentVersion     DisplayString,
        invOduCardFirmUncurrentVersion   DisplayString,
        invOduProvRangeATPCMax           Integer32,
        invOduProvRangeATPCMin           Integer32,
        invOduProvRangeMTPCMax           Integer32,
        invOduProvRangeMTPCMin           Integer32,
        invOduProvRangeRxThresholdMax    Integer32,
        invOduProvRangeRxThresholdMin    Integer32,
        invOduProvRangeHysteresisPermit  INTEGER,
        invOduProvRangeHysteresisMax     Integer32,
        invOduProvRangeHysteresisMin     Integer32,
        invOduFreqInfoTxStartFrequency   DisplayString,
        invOduFreqInfoTxStopFrequency    DisplayString,
        invOduFreqInfoRxStartFrequency   DisplayString,
        invOduFreqInfoRxStopFrequency    DisplayString,
        invOduFreqInfoFrequencyStep      DisplayString,
        invOduFreqInfoShiftFrequency     DisplayString,
        invOduFreqInfoUpperLower         INTEGER,
        invOduFreqInfoTxPhase            INTEGER,
        invOduFreqInfoRxPhase            INTEGER,
        invOduFreqInfoSubBand            DisplayString,
        invOduFreqInfoTxRxIndependence   INTEGER,
        invOduFreqInfoSupportedIpe       INTEGER,
        invOduFreqInfoSubBand1           DisplayString,
        invOduFreqInfoSubBand2           DisplayString,
        invOduFreqInfoSubBand3           DisplayString,
        invOduFreqInfoSubBand4           DisplayString,
        invOduFreqInfoSubBand5           DisplayString,
        invOduFreqInfoSubBand6           DisplayString,
        invOduFreqInfoSubBand7           DisplayString,
        invOduFreqInfoSubBand8           DisplayString,
        invOduFreqInfoSubBand9           DisplayString,
        invOduFreqInfoSubBand10          DisplayString,
        invOduSupportabilityTxPowerUp    OffOnValue,
        invOduSupportabilityHighMod      OffOnValue
    }

    invModuleInfoOduIfIndex OBJECT-TYPE
        SYNTAX       InterfaceIndex
        MAX-ACCESS   not-accessible
        STATUS       current
        DESCRIPTION  "Index of this table."
        ::= { invModuleInfoOduEntry 1 }

    invModuleInfoOduNEAddress OBJECT-TYPE
        SYNTAX       IpAddress
        MAX-ACCESS   not-accessible
        STATUS       current
        DESCRIPTION  "reserved."
        ::= { invModuleInfoOduEntry 2 }

    invOduCardName OBJECT-TYPE
        SYNTAX       DisplayString
        MAX-ACCESS   read-only
        STATUS       current
        DESCRIPTION  
            "ODU Name. when the ODU is removed or disconnected, the value
            will be changed to '**'."
        ::= { invModuleInfoOduEntry 3 }

    invOduCardCodeNo OBJECT-TYPE
        SYNTAX       DisplayString
        MAX-ACCESS   read-only
        STATUS       current
        DESCRIPTION  
            "ODU Code Name. when the ODU is removed or disconnected, the
            value will be changed to '**'."
        ::= { invModuleInfoOduEntry 4 }

    invOduCardHardVersion OBJECT-TYPE
        SYNTAX       DisplayString
        MAX-ACCESS   read-only
        STATUS       current
        DESCRIPTION  
            "ODU Hardware version. when the ODU is removed or disconnected,
            the value will be changed to '**'."
        ::= { invModuleInfoOduEntry 5 }

    invOduCardSerialNo OBJECT-TYPE
        SYNTAX       DisplayString
        MAX-ACCESS   read-only
        STATUS       current
        DESCRIPTION  
            "ODU Serial No. when the ODU is removed or disconnected, the
            value will be changed to '**'."
        ::= { invModuleInfoOduEntry 6 }

    invOduCardManufacturedDate OBJECT-TYPE
        SYNTAX       DisplayString
        MAX-ACCESS   read-only
        STATUS       current
        DESCRIPTION  
            "ODU Manufactured Date. when the ODU is removed or disconnected,
            the value will be changed to '**'."
        ::= { invModuleInfoOduEntry 7 }

    invOduCardFirmCurrentVersion OBJECT-TYPE
        SYNTAX       DisplayString
        MAX-ACCESS   read-only
        STATUS       current
        DESCRIPTION  
            "ODU Firmware information (current). when the ODU is removed or
            disconnected, the value will be changed to '**'."
        ::= { invModuleInfoOduEntry 8 }

    invOduCardFirmUncurrentVersion OBJECT-TYPE
        SYNTAX       DisplayString
        MAX-ACCESS   read-only
        STATUS       current
        DESCRIPTION  
            "ODU Firmware information (uncurrent). when the ODU is removed or
            disconnected, the value will be changed to '**'."
        ::= { invModuleInfoOduEntry 9 }

    invOduProvRangeATPCMax OBJECT-TYPE
        SYNTAX       Integer32
        MAX-ACCESS   read-only
        STATUS       current
        DESCRIPTION  "ODU Frequency Information - Range ATPC MAX (dbm)"
        ::= { invModuleInfoOduEntry 10 }

    invOduProvRangeATPCMin OBJECT-TYPE
        SYNTAX       Integer32
        MAX-ACCESS   read-only
        STATUS       current
        DESCRIPTION  "ODU Frequency Information - Range ATPC MIN (dbm)"
        ::= { invModuleInfoOduEntry 11 }

    invOduProvRangeMTPCMax OBJECT-TYPE
        SYNTAX       Integer32
        MAX-ACCESS   read-only
        STATUS       current
        DESCRIPTION  "ODU Frequency Information - Range MTPC MAX (dbm)"
        ::= { invModuleInfoOduEntry 12 }

    invOduProvRangeMTPCMin OBJECT-TYPE
        SYNTAX       Integer32
        MAX-ACCESS   read-only
        STATUS       current
        DESCRIPTION  "ODU Frequency Information - Range MTPC MIN (dbm)"
        ::= { invModuleInfoOduEntry 13 }

    invOduProvRangeRxThresholdMax OBJECT-TYPE
        SYNTAX       Integer32
        MAX-ACCESS   read-only
        STATUS       current
        DESCRIPTION  
            "ODU Frequency Information - Range RX Threshold MAX (dbm)"
        ::= { invModuleInfoOduEntry 14 }

    invOduProvRangeRxThresholdMin OBJECT-TYPE
        SYNTAX       Integer32
        MAX-ACCESS   read-only
        STATUS       current
        DESCRIPTION  
            "ODU Frequency Information - Range RX Threshold MIN (dbm)"
        ::= { invModuleInfoOduEntry 15 }

    invOduProvRangeHysteresisPermit OBJECT-TYPE
        SYNTAX       INTEGER { deny(0), permit(255) }
        MAX-ACCESS   read-only
        STATUS       current
        DESCRIPTION  "ODU Frequency Information - Range Hysteresis Permit"
        ::= { invModuleInfoOduEntry 16 }

    invOduProvRangeHysteresisMax OBJECT-TYPE
        SYNTAX       Integer32
        MAX-ACCESS   read-only
        STATUS       current
        DESCRIPTION  "ODU Range Hysteresis MAX (dB)"
        ::= { invModuleInfoOduEntry 17 }

    invOduProvRangeHysteresisMin OBJECT-TYPE
        SYNTAX       Integer32
        MAX-ACCESS   read-only
        STATUS       current
        DESCRIPTION  "ODU Range Hysteresis MIN (dB)"
        ::= { invModuleInfoOduEntry 18 }

    invOduFreqInfoTxStartFrequency OBJECT-TYPE
        SYNTAX       DisplayString
        MAX-ACCESS   read-only
        STATUS       current
        DESCRIPTION  "ODU Frequency Information - TX Start Frequency (MHz)"
        ::= { invModuleInfoOduEntry 19 }

    invOduFreqInfoTxStopFrequency OBJECT-TYPE
        SYNTAX       DisplayString
        MAX-ACCESS   read-only
        STATUS       current
        DESCRIPTION  "ODU Frequency Information - TX Stop Frequency (MHz)"
        ::= { invModuleInfoOduEntry 20 }

    invOduFreqInfoRxStartFrequency OBJECT-TYPE
        SYNTAX       DisplayString
        MAX-ACCESS   read-only
        STATUS       current
        DESCRIPTION  "ODU Frequency Information - RX Start Frequency (MHz)"
        ::= { invModuleInfoOduEntry 21 }

    invOduFreqInfoRxStopFrequency OBJECT-TYPE
        SYNTAX       DisplayString
        MAX-ACCESS   read-only
        STATUS       current
        DESCRIPTION  "ODU Frequency Information - RX Stop Frequency (MHz)"
        ::= { invModuleInfoOduEntry 22 }

    invOduFreqInfoFrequencyStep OBJECT-TYPE
        SYNTAX       DisplayString
        MAX-ACCESS   read-only
        STATUS       current
        DESCRIPTION  "ODU Frequency Information - Frequency Step (MHz)"
        ::= { invModuleInfoOduEntry 23 }

    invOduFreqInfoShiftFrequency OBJECT-TYPE
        SYNTAX       DisplayString
        MAX-ACCESS   read-only
        STATUS       current
        DESCRIPTION  "ODU Frequency Information - Shift Frequency (MHz)"
        ::= { invModuleInfoOduEntry 24 }

    invOduFreqInfoUpperLower OBJECT-TYPE
        SYNTAX       INTEGER { lower(1), upper(2) }
        MAX-ACCESS   read-only
        STATUS       current
        DESCRIPTION  "ODU Frequency Information - Upper / Lower"
        ::= { invModuleInfoOduEntry 25 }

    invOduFreqInfoTxPhase OBJECT-TYPE
        SYNTAX       INTEGER { forward(1), reverse(2) }
        MAX-ACCESS   read-only
        STATUS       current
        DESCRIPTION  "ODU Frequency Information - TX Phase"
        ::= { invModuleInfoOduEntry 26 }

    invOduFreqInfoRxPhase OBJECT-TYPE
        SYNTAX       INTEGER { forward(1), reverse(2) }
        MAX-ACCESS   read-only
        STATUS       current
        DESCRIPTION  "ODU Frequency Information - RX Phase"
        ::= { invModuleInfoOduEntry 27 }

    invOduFreqInfoSubBand OBJECT-TYPE
        SYNTAX       DisplayString
        MAX-ACCESS   read-only
        STATUS       current
        DESCRIPTION  "ODU Frequency Information - Sub Band"
        ::= { invModuleInfoOduEntry 28 }

    invOduFreqInfoTxRxIndependence OBJECT-TYPE
        SYNTAX       INTEGER { notIndependence(1), independence(2) }
        MAX-ACCESS   read-only
        STATUS       current
        DESCRIPTION  "ODU Frequency Information - TX / RX Independence"
        ::= { invModuleInfoOduEntry 29 }

    invOduFreqInfoSupportedIpe OBJECT-TYPE
        SYNTAX       INTEGER { notSupported(1), supported(2) }
        MAX-ACCESS   read-only
        STATUS       current
        DESCRIPTION  "ODU Frequency Information - Supported iPASOLINK"
        ::= { invModuleInfoOduEntry 30 }

    invOduFreqInfoSubBand1 OBJECT-TYPE
        SYNTAX       DisplayString
        MAX-ACCESS   read-only
        STATUS       current
        DESCRIPTION  "ODU Frequency Information - Sub Band 01"
        ::= { invModuleInfoOduEntry 31 }

    invOduFreqInfoSubBand2 OBJECT-TYPE
        SYNTAX       DisplayString
        MAX-ACCESS   read-only
        STATUS       current
        DESCRIPTION  "ODU Frequency Information - Sub Band 02"
        ::= { invModuleInfoOduEntry 32 }

    invOduFreqInfoSubBand3 OBJECT-TYPE
        SYNTAX       DisplayString
        MAX-ACCESS   read-only
        STATUS       current
        DESCRIPTION  "ODU Frequency Information - Sub Band 03"
        ::= { invModuleInfoOduEntry 33 }

    invOduFreqInfoSubBand4 OBJECT-TYPE
        SYNTAX       DisplayString
        MAX-ACCESS   read-only
        STATUS       current
        DESCRIPTION  "ODU Frequency Information - Sub Band 04"
        ::= { invModuleInfoOduEntry 34 }

    invOduFreqInfoSubBand5 OBJECT-TYPE
        SYNTAX       DisplayString
        MAX-ACCESS   read-only
        STATUS       current
        DESCRIPTION  "ODU Frequency Information - Sub Band 05"
        ::= { invModuleInfoOduEntry 35 }

    invOduFreqInfoSubBand6 OBJECT-TYPE
        SYNTAX       DisplayString
        MAX-ACCESS   read-only
        STATUS       current
        DESCRIPTION  "ODU Frequency Information - Sub Band 06"
        ::= { invModuleInfoOduEntry 36 }

    invOduFreqInfoSubBand7 OBJECT-TYPE
        SYNTAX       DisplayString
        MAX-ACCESS   read-only
        STATUS       current
        DESCRIPTION  "ODU Frequency Information - Sub Band 07"
        ::= { invModuleInfoOduEntry 37 }

    invOduFreqInfoSubBand8 OBJECT-TYPE
        SYNTAX       DisplayString
        MAX-ACCESS   read-only
        STATUS       current
        DESCRIPTION  "ODU Frequency Information - Sub Band 08"
        ::= { invModuleInfoOduEntry 38 }

    invOduFreqInfoSubBand9 OBJECT-TYPE
        SYNTAX       DisplayString
        MAX-ACCESS   read-only
        STATUS       current
        DESCRIPTION  "ODU Frequency Information - Sub Band 09"
        ::= { invModuleInfoOduEntry 39 }

    invOduFreqInfoSubBand10 OBJECT-TYPE
        SYNTAX       DisplayString
        MAX-ACCESS   read-only
        STATUS       current
        DESCRIPTION  "ODU Frequency Information - Sub Band 10"
        ::= { invModuleInfoOduEntry 40 }

    invOduSupportabilityTxPowerUp OBJECT-TYPE
        SYNTAX       OffOnValue
        MAX-ACCESS   read-only
        STATUS       current
        DESCRIPTION  
            "This object shows whether the ODU/RF unit has the capability for
            TX Power Up function or not."
        ::= { invModuleInfoOduEntry 46 }

    invOduSupportabilityHighMod OBJECT-TYPE
        SYNTAX       OffOnValue
        MAX-ACCESS   read-only
        STATUS       current
        DESCRIPTION  
            "This object shows whether the ODU/RF unit has the capability for
            High Modulation function or not."
        ::= { invModuleInfoOduEntry 47 }

    invUpdateInfoTable OBJECT-TYPE
        SYNTAX       SEQUENCE OF InvUpdateInfoEntry
        MAX-ACCESS   not-accessible
        STATUS       current
        DESCRIPTION  "Inventory Update Information"
        ::= { inventoryGroup 4 }

    invUpdateInfoEntry OBJECT-TYPE
        SYNTAX       InvUpdateInfoEntry
        MAX-ACCESS   not-accessible
        STATUS       current
        DESCRIPTION  ""
        INDEX        { invUpdateInfoIndex }
        ::= { invUpdateInfoTable 1 }

    InvUpdateInfoEntry ::= SEQUENCE {
        invUpdateInfoIndex      Integer32,
        invUpdateInfoNEAddress  IpAddress,
        invUpdateInfoSummary    OCTET STRING
    }

    invUpdateInfoIndex OBJECT-TYPE
        SYNTAX       Integer32 (1..1)
        MAX-ACCESS   not-accessible
        STATUS       current
        DESCRIPTION  "Index of this table."
        ::= { invUpdateInfoEntry 1 }

    invUpdateInfoNEAddress OBJECT-TYPE
        SYNTAX       IpAddress
        MAX-ACCESS   not-accessible
        STATUS       current
        DESCRIPTION  "reserved."
        ::= { invUpdateInfoEntry 2 }

    invUpdateInfoSummary OBJECT-TYPE
        SYNTAX       OCTET STRING (SIZE(12..12|20..20))
        MAX-ACCESS   read-only
        STATUS       current
        DESCRIPTION  "Inventory Update Information Summary"
        ::= { invUpdateInfoEntry 3 }

    invSfpInfoTable OBJECT-TYPE
        SYNTAX       SEQUENCE OF InvSfpInfoEntry
        MAX-ACCESS   not-accessible
        STATUS       current
        DESCRIPTION  "SFP / XFP Information"
        ::= { inventoryGroup 5 }

    invSfpInfoEntry OBJECT-TYPE
        SYNTAX       InvSfpInfoEntry
        MAX-ACCESS   not-accessible
        STATUS       current
        DESCRIPTION  ""
        INDEX        { invSfpInfoIfIndex }
        ::= { invSfpInfoTable 1 }

    InvSfpInfoEntry ::= SEQUENCE {
        invSfpInfoIfIndex          InterfaceIndex,
        invSfpInfoNEAddress        IpAddress,
        invSfpVendorName           DisplayString,
        invSfpVendorPn             DisplayString,
        invSfpVendorVer            DisplayString,
        invSfpVendorSn             DisplayString,
        invSfpType                 DisplayString,
        invSfpManufacturedDate     DisplayString,
        invSfpSupportedWavelength  DisplayString,
        invSfpSupportedLinkLength  DisplayString
    }

    invSfpInfoIfIndex OBJECT-TYPE
        SYNTAX       InterfaceIndex
        MAX-ACCESS   not-accessible
        STATUS       current
        DESCRIPTION  "Index of this table."
        ::= { invSfpInfoEntry 1 }

    invSfpInfoNEAddress OBJECT-TYPE
        SYNTAX       IpAddress
        MAX-ACCESS   not-accessible
        STATUS       current
        DESCRIPTION  "reserved."
        ::= { invSfpInfoEntry 2 }

    invSfpVendorName OBJECT-TYPE
        SYNTAX       DisplayString
        MAX-ACCESS   read-only
        STATUS       current
        DESCRIPTION  "Vendor Name"
        ::= { invSfpInfoEntry 3 }

    invSfpVendorPn OBJECT-TYPE
        SYNTAX       DisplayString
        MAX-ACCESS   read-only
        STATUS       current
        DESCRIPTION  "Part Number"
        ::= { invSfpInfoEntry 4 }

    invSfpVendorVer OBJECT-TYPE
        SYNTAX       DisplayString
        MAX-ACCESS   read-only
        STATUS       current
        DESCRIPTION  "Vendor Revision Number"
        ::= { invSfpInfoEntry 5 }

    invSfpVendorSn OBJECT-TYPE
        SYNTAX       DisplayString
        MAX-ACCESS   read-only
        STATUS       current
        DESCRIPTION  "Vendor Serial Number"
        ::= { invSfpInfoEntry 6 }

    invSfpType OBJECT-TYPE
        SYNTAX       DisplayString
        MAX-ACCESS   read-only
        STATUS       current
        DESCRIPTION  "SFP Type"
        ::= { invSfpInfoEntry 7 }

    invSfpManufacturedDate OBJECT-TYPE
        SYNTAX       DisplayString
        MAX-ACCESS   read-only
        STATUS       current
        DESCRIPTION  "SFP Manufactured Date"
        ::= { invSfpInfoEntry 8 }

    invSfpSupportedWavelength OBJECT-TYPE
        SYNTAX       DisplayString
        UNITS        "nm"
        MAX-ACCESS   read-only
        STATUS       current
        DESCRIPTION  
            "Wavelength supported by SFP/XFP/SFP+.
            If the SFP media type is not optical, this object will show the
            value '0'."
        ::= { invSfpInfoEntry 9 }

    invSfpSupportedLinkLength OBJECT-TYPE
        SYNTAX       DisplayString
        UNITS        "km"
        MAX-ACCESS   read-only
        STATUS       current
        DESCRIPTION  "Link length supported by SFP/XFP/SFP+."
        ::= { invSfpInfoEntry 10 }

    invSoftkeyInfoTable OBJECT-TYPE
        SYNTAX       SEQUENCE OF InvSoftkeyInfoEntry
        MAX-ACCESS   not-accessible
        STATUS       current
        DESCRIPTION  "Software Key Information."
        ::= { inventoryGroup 6 }

    invSoftkeyInfoEntry OBJECT-TYPE
        SYNTAX       InvSoftkeyInfoEntry
        MAX-ACCESS   not-accessible
        STATUS       current
        DESCRIPTION  ""
        INDEX        { invSoftkeyInfoIndex }
        ::= { invSoftkeyInfoTable 1 }

    InvSoftkeyInfoEntry ::= SEQUENCE {
        invSoftkeyInfoIndex          Integer32,
        invSoftkeyInfoNEAddress      IpAddress,
        invSoftkeySerialNo           DisplayString,
        invSupportabilityInfoFw      OCTET STRING,
        invSupportabilityInfoKey     OCTET STRING,
        invSupportabilityInfoValid   OCTET STRING,
        invCapa10MaxE1Rst            OCTET STRING,
        invCapa20MaxE1Rst            OCTET STRING,
        invCapa50MaxE1Rst            OCTET STRING,
        invCapa100MaxE1Rst           OCTET STRING,
        invCapa150MaxE1Rst           OCTET STRING,
        invCapa200MaxE1Rst           OCTET STRING,
        invCapa300MaxE1Rst           OCTET STRING,
        invCapa400MaxE1Rst           OCTET STRING,
        invSoftkeyEquipmentSerialNo  DisplayString
    }

    invSoftkeyInfoIndex OBJECT-TYPE
        SYNTAX       Integer32 (1..1)
        MAX-ACCESS   not-accessible
        STATUS       current
        DESCRIPTION  "Index of this table."
        ::= { invSoftkeyInfoEntry 1 }

    invSoftkeyInfoNEAddress OBJECT-TYPE
        SYNTAX       IpAddress
        MAX-ACCESS   not-accessible
        STATUS       current
        DESCRIPTION  "reserved"
        ::= { invSoftkeyInfoEntry 2 }

    invSoftkeySerialNo OBJECT-TYPE
        SYNTAX       DisplayString
        MAX-ACCESS   read-only
        STATUS       current
        DESCRIPTION  "Software Key Serial No."
        ::= { invSoftkeyInfoEntry 3 }

    invSupportabilityInfoFw OBJECT-TYPE
        SYNTAX       OCTET STRING (SIZE(32..32|40..40|52..52|60..60|68..68|72..72))
        MAX-ACCESS   read-only
        STATUS       current
        DESCRIPTION  "Supportability (Firmware)"
        ::= { invSoftkeyInfoEntry 4 }

    invSupportabilityInfoKey OBJECT-TYPE
        SYNTAX       OCTET STRING (SIZE(32..32|40..40|52..52|60..60|68..68|72..72))
        MAX-ACCESS   read-only
        STATUS       current
        DESCRIPTION  "Supportability (Software Key)"
        ::= { invSoftkeyInfoEntry 5 }

    invSupportabilityInfoValid OBJECT-TYPE
        SYNTAX       OCTET STRING (SIZE(32..32|40..40|52..52|60..60|68..68|72..72))
        MAX-ACCESS   read-only
        STATUS       current
        DESCRIPTION  "Supportability (Current)"
        ::= { invSoftkeyInfoEntry 6 }

    invCapa10MaxE1Rst OBJECT-TYPE
        SYNTAX       OCTET STRING (SIZE(160..160|192..192))
        MAX-ACCESS   read-only
        STATUS       current
        DESCRIPTION  
            "Maximum Available E1/RST Connections for 10M Capacity."
        ::= { invSoftkeyInfoEntry 7 }

    invCapa20MaxE1Rst OBJECT-TYPE
        SYNTAX       OCTET STRING (SIZE(160..160|192..192))
        MAX-ACCESS   read-only
        STATUS       current
        DESCRIPTION  
            "Maximum Available E1/RST Connections for 20M Capacity."
        ::= { invSoftkeyInfoEntry 8 }

    invCapa50MaxE1Rst OBJECT-TYPE
        SYNTAX       OCTET STRING (SIZE(160..160|192..192))
        MAX-ACCESS   read-only
        STATUS       current
        DESCRIPTION  
            "Maximum Available E1/RST Connections for 50M Capacity."
        ::= { invSoftkeyInfoEntry 9 }

    invCapa100MaxE1Rst OBJECT-TYPE
        SYNTAX       OCTET STRING (SIZE(160..160|192..192))
        MAX-ACCESS   read-only
        STATUS       current
        DESCRIPTION  
            "Maximum Available E1/RST Connections for 100M Capacity."
        ::= { invSoftkeyInfoEntry 10 }

    invCapa150MaxE1Rst OBJECT-TYPE
        SYNTAX       OCTET STRING (SIZE(160..160|192..192))
        MAX-ACCESS   read-only
        STATUS       current
        DESCRIPTION  
            "Maximum Available E1/RST Connections for 150M Capacity."
        ::= { invSoftkeyInfoEntry 11 }

    invCapa200MaxE1Rst OBJECT-TYPE
        SYNTAX       OCTET STRING (SIZE(160..160|192..192))
        MAX-ACCESS   read-only
        STATUS       current
        DESCRIPTION  
            "Maximum Available E1/RST Connections for 200M Capacity."
        ::= { invSoftkeyInfoEntry 12 }

    invCapa300MaxE1Rst OBJECT-TYPE
        SYNTAX       OCTET STRING (SIZE(160..160|192..192))
        MAX-ACCESS   read-only
        STATUS       current
        DESCRIPTION  
            "Maximum Available E1/RST Connections for 300M Capacity."
        ::= { invSoftkeyInfoEntry 13 }

    invCapa400MaxE1Rst OBJECT-TYPE
        SYNTAX       OCTET STRING (SIZE(160..160|192..192))
        MAX-ACCESS   read-only
        STATUS       current
        DESCRIPTION  
            "Maximum Available E1/RST Connections for 400M Capacity."
        ::= { invSoftkeyInfoEntry 14 }

    invSoftkeyEquipmentSerialNo OBJECT-TYPE
        SYNTAX       DisplayString
        MAX-ACCESS   read-only
        STATUS       obsolete
        DESCRIPTION  "Equipment Serial Number."
        ::= { invSoftkeyInfoEntry 15 }

    invMacAddressInfoTable OBJECT-TYPE
        SYNTAX       SEQUENCE OF InvMacAddressInfoEntry
        MAX-ACCESS   not-accessible
        STATUS       current
        DESCRIPTION  
            "Equipment Inventory Information - Mac Address Information"
        ::= { inventoryGroup 8 }

    invMacAddressInfoEntry OBJECT-TYPE
        SYNTAX       InvMacAddressInfoEntry
        MAX-ACCESS   not-accessible
        STATUS       current
        DESCRIPTION  ""
        INDEX        { invMacAddressInfoIfIndex }
        ::= { invMacAddressInfoTable 1 }

    InvMacAddressInfoEntry ::= SEQUENCE {
        invMacAddressInfoIfIndex    InterfaceIndex,
        invMacAddressInfoNEAddress  IpAddress,
        invMacAddress               MacAddress
    }

    invMacAddressInfoIfIndex OBJECT-TYPE
        SYNTAX       InterfaceIndex
        MAX-ACCESS   not-accessible
        STATUS       current
        DESCRIPTION  "Index of this table."
        ::= { invMacAddressInfoEntry 1 }

    invMacAddressInfoNEAddress OBJECT-TYPE
        SYNTAX       IpAddress
        MAX-ACCESS   not-accessible
        STATUS       current
        DESCRIPTION  "reserved"
        ::= { invMacAddressInfoEntry 2 }

    invMacAddress OBJECT-TYPE
        SYNTAX       MacAddress
        MAX-ACCESS   read-only
        STATUS       current
        DESCRIPTION  "Mac Address which assigned to that port."
        ::= { invMacAddressInfoEntry 3 }

    invModemParamInfoTable OBJECT-TYPE
        SYNTAX       SEQUENCE OF InvModemParamInfoEntry
        MAX-ACCESS   not-accessible
        STATUS       current
        DESCRIPTION  
            "Equipment Inventory Information (IDU) - MODEM Parameter"
        ::= { inventoryGroup 9 }

    invModemParamInfoEntry OBJECT-TYPE
        SYNTAX       InvModemParamInfoEntry
        MAX-ACCESS   not-accessible
        STATUS       current
        DESCRIPTION  ""
        INDEX        { invModemParamInfoIfIndex }
        ::= { invModemParamInfoTable 1 }

    InvModemParamInfoEntry ::= SEQUENCE {
        invModemParamInfoIfIndex    InterfaceIndex,
        invModemParamInfoNEAddress  IpAddress,
        invModemParamVersion        DisplayString
    }

    invModemParamInfoIfIndex OBJECT-TYPE
        SYNTAX       InterfaceIndex
        MAX-ACCESS   not-accessible
        STATUS       current
        DESCRIPTION  "Index of this table."
        ::= { invModemParamInfoEntry 1 }

    invModemParamInfoNEAddress OBJECT-TYPE
        SYNTAX       IpAddress
        MAX-ACCESS   not-accessible
        STATUS       current
        DESCRIPTION  "reserved."
        ::= { invModemParamInfoEntry 2 }

    invModemParamVersion OBJECT-TYPE
        SYNTAX       DisplayString
        MAX-ACCESS   read-only
        STATUS       current
        DESCRIPTION  
            "Parameter Information
            MIB format of invModemParamVersion is xx.yy."
        ::= { invModemParamInfoEntry 3 }

    invChassisInfoTable OBJECT-TYPE
        SYNTAX       SEQUENCE OF InvChassisInfoEntry
        MAX-ACCESS   not-accessible
        STATUS       current
        DESCRIPTION  "Equipment Inventory Information (IDU) - Chassis"
        ::= { inventoryGroup 10 }

    invChassisInfoEntry OBJECT-TYPE
        SYNTAX       InvChassisInfoEntry
        MAX-ACCESS   not-accessible
        STATUS       current
        DESCRIPTION  ""
        INDEX        { invChassisInfoIndex }
        ::= { invChassisInfoTable 1 }

    InvChassisInfoEntry ::= SEQUENCE {
        invChassisInfoIndex         Integer32,
        invChassisInfoNEAddress     IpAddress,
        invChassisName              DisplayString,
        invChassisCodeNo            DisplayString,
        invChassisSerialNo          DisplayString,
        invChassisManufacturedDate  DisplayString,
        invChassisFirmVersion       DisplayString,
        invChassisHardVersion       DisplayString
    }

    invChassisInfoIndex OBJECT-TYPE
        SYNTAX       Integer32 (1..1)
        MAX-ACCESS   not-accessible
        STATUS       current
        DESCRIPTION  "Index of this table."
        ::= { invChassisInfoEntry 1 }

    invChassisInfoNEAddress OBJECT-TYPE
        SYNTAX       IpAddress
        MAX-ACCESS   not-accessible
        STATUS       current
        DESCRIPTION  "reserved."
        ::= { invChassisInfoEntry 2 }

    invChassisName OBJECT-TYPE
        SYNTAX       DisplayString
        MAX-ACCESS   read-only
        STATUS       current
        DESCRIPTION  "Name"
        ::= { invChassisInfoEntry 3 }

    invChassisCodeNo OBJECT-TYPE
        SYNTAX       DisplayString
        MAX-ACCESS   read-only
        STATUS       current
        DESCRIPTION  "Code No."
        ::= { invChassisInfoEntry 4 }

    invChassisSerialNo OBJECT-TYPE
        SYNTAX       DisplayString (SIZE(1..8))
        MAX-ACCESS   read-write
        STATUS       current
        DESCRIPTION  
            "Serial No.
            Note: For VR 2, this object cannot be modified, acting as
            read-only object."
        ::= { invChassisInfoEntry 5 }

    invChassisManufacturedDate OBJECT-TYPE
        SYNTAX       DisplayString (SIZE(1..7))
        MAX-ACCESS   read-write
        STATUS       current
        DESCRIPTION  
            "Manufactured Date
            Note: For VR 2, this object cannot be modified, acting as
            read-only object."
        ::= { invChassisInfoEntry 6 }

    invChassisFirmVersion OBJECT-TYPE
        SYNTAX       DisplayString
        MAX-ACCESS   read-only
        STATUS       current
        DESCRIPTION  "Firmware Version"
        ::= { invChassisInfoEntry 7 }

    invChassisHardVersion OBJECT-TYPE
        SYNTAX       DisplayString
        MAX-ACCESS   read-only
        STATUS       current
        DESCRIPTION  "Hardware Version"
        ::= { invChassisInfoEntry 8 }

    invMainOptionInfoTable OBJECT-TYPE
        SYNTAX       SEQUENCE OF InvMainOptionInfoEntry
        MAX-ACCESS   not-accessible
        STATUS       current
        DESCRIPTION  
            "Supportability information for the optional functions."
        ::= { inventoryGroup 12 }

    invMainOptionInfoEntry OBJECT-TYPE
        SYNTAX       InvMainOptionInfoEntry
        MAX-ACCESS   not-accessible
        STATUS       current
        DESCRIPTION  ""
        INDEX        { invMainOptionInfoIndex }
        ::= { invMainOptionInfoTable 1 }

    InvMainOptionInfoEntry ::= SEQUENCE {
        invMainOptionInfoIndex                Integer32,
        invMainOptionInfoNEAddress            IpAddress,
        invSupportabilityMainOptionInfoHw     OCTET STRING,
        invSupportabilityMainOptionInfoFw     OCTET STRING,
        invSupportabilityMainOptionInfoValid  OCTET STRING
    }

    invMainOptionInfoIndex OBJECT-TYPE
        SYNTAX       Integer32 (1..1)
        MAX-ACCESS   not-accessible
        STATUS       current
        DESCRIPTION  "Index of this table."
        ::= { invMainOptionInfoEntry 1 }

    invMainOptionInfoNEAddress OBJECT-TYPE
        SYNTAX       IpAddress
        MAX-ACCESS   not-accessible
        STATUS       current
        DESCRIPTION  "reserved"
        ::= { invMainOptionInfoEntry 2 }

    invSupportabilityMainOptionInfoHw OBJECT-TYPE
        SYNTAX       OCTET STRING (SIZE(16..16))
        MAX-ACCESS   read-only
        STATUS       current
        DESCRIPTION  "Supportability (Hardware)"
        ::= { invMainOptionInfoEntry 3 }

    invSupportabilityMainOptionInfoFw OBJECT-TYPE
        SYNTAX       OCTET STRING (SIZE(16..16))
        MAX-ACCESS   read-only
        STATUS       current
        DESCRIPTION  "Supportability (Firmware)"
        ::= { invMainOptionInfoEntry 4 }

    invSupportabilityMainOptionInfoValid OBJECT-TYPE
        SYNTAX       OCTET STRING (SIZE(16..16))
        MAX-ACCESS   read-only
        STATUS       current
        DESCRIPTION  "Supportability (Current)"
        ::= { invMainOptionInfoEntry 5 }

    invSupportCsInfoTable OBJECT-TYPE
        SYNTAX       SEQUENCE OF InvSupportCsInfoEntry
        MAX-ACCESS   not-accessible
        STATUS       current
        DESCRIPTION  "Equipment Support CS(Channel Spacing) Information."
        ::= { inventoryGroup 14 }

    invSupportCsInfoEntry OBJECT-TYPE
        SYNTAX       InvSupportCsInfoEntry
        MAX-ACCESS   not-accessible
        STATUS       current
        DESCRIPTION  ""
        INDEX        { invSupportCsInfoIfIndex }
        ::= { invSupportCsInfoTable 1 }

    InvSupportCsInfoEntry ::= SEQUENCE {
        invSupportCsInfoIfIndex    InterfaceIndex,
        invSupportCsInfoNEAddress  IpAddress,
        invSupportCsValue62Dot5M   OffOnValue,
        invSupportCsValue125M      OffOnValue,
        invSupportCsValue250M      OffOnValue,
        invSupportCsValue500M      OffOnValue,
        invSupportCsValue750M      OffOnValue,
        invSupportCsValue1000M     OffOnValue,
        invSupportCsValue2000M     OffOnValue,
        invSupportCsValue1500M     OffOnValue
    }

    invSupportCsInfoIfIndex OBJECT-TYPE
        SYNTAX       InterfaceIndex
        MAX-ACCESS   not-accessible
        STATUS       current
        DESCRIPTION  "Index of this table."
        ::= { invSupportCsInfoEntry 1 }

    invSupportCsInfoNEAddress OBJECT-TYPE
        SYNTAX       IpAddress
        MAX-ACCESS   not-accessible
        STATUS       current
        DESCRIPTION  "reserved."
        ::= { invSupportCsInfoEntry 2 }

    invSupportCsValue62Dot5M OBJECT-TYPE
        SYNTAX       OffOnValue
        MAX-ACCESS   read-only
        STATUS       current
        DESCRIPTION  
            "Information of Supportting CS(Channel Spacing).
            If invSupportCsValue62point5M is not 'on', esModemChSpacing of
            'cs62Dot5m' can not be set. (iPASOLINK EX Advanced)"
        ::= { invSupportCsInfoEntry 3 }

    invSupportCsValue125M OBJECT-TYPE
        SYNTAX       OffOnValue
        MAX-ACCESS   read-only
        STATUS       current
        DESCRIPTION  
            "Information of Supportting CS(Channel Spacing).
            If invSupportCsValue125M is not 'on', esModemChSpacing of
            'cs125m' can not be set. (iPASOLINK EX Advanced)"
        ::= { invSupportCsInfoEntry 4 }

    invSupportCsValue250M OBJECT-TYPE
        SYNTAX       OffOnValue
        MAX-ACCESS   read-only
        STATUS       current
        DESCRIPTION  
            "Information of Supportting CS(Channel Spacing).
            If invSupportCsValue250M is not 'on', esModemChSpacing of
            'cs250m' can not be set. (iPASOLINK EX Advanced)"
        ::= { invSupportCsInfoEntry 5 }

    invSupportCsValue500M OBJECT-TYPE
        SYNTAX       OffOnValue
        MAX-ACCESS   read-only
        STATUS       current
        DESCRIPTION  
            "Information of Supportting CS(Channel Spacing).
            If invSupportCsValue500M is not 'on', esModemChSpacing of
            'cs500m' can not be set. (iPASOLINK EX Advanced)"
        ::= { invSupportCsInfoEntry 6 }

    invSupportCsValue750M OBJECT-TYPE
        SYNTAX       OffOnValue
        MAX-ACCESS   read-only
        STATUS       current
        DESCRIPTION  
            "Information of Supportting CS(Channel Spacing).
            If invSupportCsValue750M is not 'on', esModemChSpacing of
            'cs750m' can not be set. (iPASOLINK EX Advanced)"
        ::= { invSupportCsInfoEntry 7 }

    invSupportCsValue1000M OBJECT-TYPE
        SYNTAX       OffOnValue
        MAX-ACCESS   read-only
        STATUS       current
        DESCRIPTION  
            "Information of Supportting CS(Channel Spacing).
            If invSupportCsValue1000M is not 'on', esModemChSpacing of
            'cs1000m' can not be set. (iPASOLINK EX Advanced)"
        ::= { invSupportCsInfoEntry 8 }

    invSupportCsValue2000M OBJECT-TYPE
        SYNTAX       OffOnValue
        MAX-ACCESS   read-only
        STATUS       current
        DESCRIPTION  
            "Information of Supportting CS(Channel Spacing).
            If invSupportCsValue2000M is not 'on', esModemChSpacing of
            'cs2000m' can not be set. (iPASOLINK EX Advanced)"
        ::= { invSupportCsInfoEntry 9 }

    invSupportCsValue1500M OBJECT-TYPE
        SYNTAX       OffOnValue
        MAX-ACCESS   read-only
        STATUS       current
        DESCRIPTION  
            "Information of Supportting CS(Channel Spacing).
            If invSupportCsValue1500M is not 'on', esModemChSpacing of
            'cs1500m' can not be set. (iPASOLINK EX Advanced)"
        ::= { invSupportCsInfoEntry 10 }

    invControllerInfoTable OBJECT-TYPE
        SYNTAX       SEQUENCE OF InvControllerInfoEntry
        MAX-ACCESS   not-accessible
        STATUS       current
        DESCRIPTION  "Equipment Inventory Information (IDU) - Controller"
        ::= { inventoryGroup 15 }

    invControllerInfoEntry OBJECT-TYPE
        SYNTAX       InvControllerInfoEntry
        MAX-ACCESS   not-accessible
        STATUS       current
        DESCRIPTION  ""
        INDEX        { invControllerInfoIndex }
        ::= { invControllerInfoTable 1 }

    InvControllerInfoEntry ::= SEQUENCE {
        invControllerInfoIndex      Integer32,
        invControllerInfoNEAddress  IpAddress,
        invControllerName           DisplayString,
        invControllerCodeNo         DisplayString,
        invControllerVersion        DisplayString
    }

    invControllerInfoIndex OBJECT-TYPE
        SYNTAX       Integer32
        MAX-ACCESS   not-accessible
        STATUS       current
        DESCRIPTION  "Index of this table."
        ::= { invControllerInfoEntry 1 }

    invControllerInfoNEAddress OBJECT-TYPE
        SYNTAX       IpAddress
        MAX-ACCESS   not-accessible
        STATUS       current
        DESCRIPTION  "reserved."
        ::= { invControllerInfoEntry 2 }

    invControllerName OBJECT-TYPE
        SYNTAX       DisplayString
        MAX-ACCESS   read-only
        STATUS       current
        DESCRIPTION  
            "Controller Name. when the card is removed or the card doesn't
            have controller, the value will be changed to '**'."
        ::= { invControllerInfoEntry 3 }

    invControllerCodeNo OBJECT-TYPE
        SYNTAX       DisplayString
        MAX-ACCESS   read-only
        STATUS       current
        DESCRIPTION  
            "Controller Code No. when the card is removed or the card doesn't
            have controller, the value will be changed to '**'."
        ::= { invControllerInfoEntry 4 }

    invControllerVersion OBJECT-TYPE
        SYNTAX       DisplayString
        MAX-ACCESS   read-only
        STATUS       current
        DESCRIPTION  
            "Controller Version. when the card is removed or the card doesn't
            have controller, the value will be changed to '**'.
            MIB format of invControllerVersion is xx.yy."
        ::= { invControllerInfoEntry 5 }

    meteringTable OBJECT-TYPE
        SYNTAX       SEQUENCE OF MeteringEntry
        MAX-ACCESS   not-accessible
        STATUS       current
        DESCRIPTION  "MODEM TX / RX Metering Table."
        ::= { meteringGroup 1 }

    meteringEntry OBJECT-TYPE
        SYNTAX       MeteringEntry
        MAX-ACCESS   not-accessible
        STATUS       current
        DESCRIPTION  ""
        INDEX        { meteringIfIndex }
        ::= { meteringTable 1 }

    MeteringEntry ::= SEQUENCE {
        meteringIfIndex           InterfaceIndex,
        meteringNEAddress         IpAddress,
        metSysTxPowerStatus       ValidInvalidValue,
        metSysTxPowerValue        DisplayString,
        metSysRxLevelStatus       ValidInvalidValue,
        metSysRxLevelValue        DisplayString,
        metSysPSVoltageStatus     ValidInvalidValue,
        metSysPSVoltageValue      DisplayString,
        metSysTempIDUStatus       ValidInvalidValue,
        metSysTempIDUValue        DisplayString,
        metSysBitErrorRateStatus  Integer32,
        metSysBitErrorRateValue   DisplayString,
        metSysXpdStatus           ValidInvalidValue,
        metSysXpdValue            DisplayString
    }

    meteringIfIndex OBJECT-TYPE
        SYNTAX       InterfaceIndex
        MAX-ACCESS   not-accessible
        STATUS       current
        DESCRIPTION  "index of this table."
        ::= { meteringEntry 1 }

    meteringNEAddress OBJECT-TYPE
        SYNTAX       IpAddress
        MAX-ACCESS   not-accessible
        STATUS       current
        DESCRIPTION  "reserved."
        ::= { meteringEntry 2 }

    metSysTxPowerStatus OBJECT-TYPE
        SYNTAX       ValidInvalidValue
        MAX-ACCESS   read-only
        STATUS       current
        DESCRIPTION  "MODEM TX Power Status."
        ::= { meteringEntry 3 }

    metSysTxPowerValue OBJECT-TYPE
        SYNTAX       DisplayString
        MAX-ACCESS   read-only
        STATUS       current
        DESCRIPTION  "MODEM TX Power"
        ::= { meteringEntry 4 }

    metSysRxLevelStatus OBJECT-TYPE
        SYNTAX       ValidInvalidValue
        MAX-ACCESS   read-only
        STATUS       current
        DESCRIPTION  "MODEM RX Power Status"
        ::= { meteringEntry 5 }

    metSysRxLevelValue OBJECT-TYPE
        SYNTAX       DisplayString
        MAX-ACCESS   read-only
        STATUS       current
        DESCRIPTION  "MODEM RX Power"
        ::= { meteringEntry 6 }

    metSysPSVoltageStatus OBJECT-TYPE
        SYNTAX       ValidInvalidValue
        MAX-ACCESS   read-only
        STATUS       current
        DESCRIPTION  "MODEM ODU Power Supply Status"
        ::= { meteringEntry 7 }

    metSysPSVoltageValue OBJECT-TYPE
        SYNTAX       DisplayString
        MAX-ACCESS   read-only
        STATUS       current
        DESCRIPTION  "MODEM ODU Power Supply"
        ::= { meteringEntry 8 }

    metSysTempIDUStatus OBJECT-TYPE
        SYNTAX       ValidInvalidValue
        MAX-ACCESS   read-only
        STATUS       current
        DESCRIPTION  "IDU Temperature Status"
        ::= { meteringEntry 11 }

    metSysTempIDUValue OBJECT-TYPE
        SYNTAX       DisplayString
        MAX-ACCESS   read-only
        STATUS       current
        DESCRIPTION  "IDU Temperature"
        ::= { meteringEntry 12 }

    metSysBitErrorRateStatus OBJECT-TYPE
        SYNTAX       Integer32
        MAX-ACCESS   read-only
        STATUS       current
        DESCRIPTION  "MODEM BER Status"
        ::= { meteringEntry 13 }

    metSysBitErrorRateValue OBJECT-TYPE
        SYNTAX       DisplayString
        MAX-ACCESS   read-only
        STATUS       current
        DESCRIPTION  "MODEM BER"
        ::= { meteringEntry 14 }

    metSysXpdStatus OBJECT-TYPE
        SYNTAX       ValidInvalidValue
        MAX-ACCESS   read-only
        STATUS       current
        DESCRIPTION  "XPD Status"
        ::= { meteringEntry 19 }

    metSysXpdValue OBJECT-TYPE
        SYNTAX       DisplayString
        MAX-ACCESS   read-only
        STATUS       current
        DESCRIPTION  "XPD. The unit of this value is dB."
        ::= { meteringEntry 20 }

    meteringSfpTable OBJECT-TYPE
        SYNTAX       SEQUENCE OF MeteringSfpEntry
        MAX-ACCESS   not-accessible
        STATUS       current
        DESCRIPTION  "SFP Metering Table"
        ::= { meteringGroup 2 }

    meteringSfpEntry OBJECT-TYPE
        SYNTAX       MeteringSfpEntry
        MAX-ACCESS   not-accessible
        STATUS       current
        DESCRIPTION  ""
        INDEX        { meteringSfpIfIndex }
        ::= { meteringSfpTable 1 }

    MeteringSfpEntry ::= SEQUENCE {
        meteringSfpIfIndex        InterfaceIndex,
        meteringSfpNEAddress      IpAddress,
        meteringSfpTxPower        DisplayString,
        meteringSfpTxPowerStatus  ValidInvalidValue,
        meteringSfpRxPower        DisplayString,
        meteringSfpRxPowerStatus  ValidInvalidValue
    }

    meteringSfpIfIndex OBJECT-TYPE
        SYNTAX       InterfaceIndex
        MAX-ACCESS   not-accessible
        STATUS       current
        DESCRIPTION  "Index of this table."
        ::= { meteringSfpEntry 1 }

    meteringSfpNEAddress OBJECT-TYPE
        SYNTAX       IpAddress
        MAX-ACCESS   not-accessible
        STATUS       current
        DESCRIPTION  "reserved."
        ::= { meteringSfpEntry 2 }

    meteringSfpTxPower OBJECT-TYPE
        SYNTAX       DisplayString
        MAX-ACCESS   read-only
        STATUS       current
        DESCRIPTION  "SFP TX Power [in dBm]"
        ::= { meteringSfpEntry 3 }

    meteringSfpTxPowerStatus OBJECT-TYPE
        SYNTAX       ValidInvalidValue
        MAX-ACCESS   read-only
        STATUS       current
        DESCRIPTION  "SFP TX Power Status"
        ::= { meteringSfpEntry 4 }

    meteringSfpRxPower OBJECT-TYPE
        SYNTAX       DisplayString
        MAX-ACCESS   read-only
        STATUS       current
        DESCRIPTION  "SFP RX Power [in dBm]"
        ::= { meteringSfpEntry 5 }

    meteringSfpRxPowerStatus OBJECT-TYPE
        SYNTAX       ValidInvalidValue
        MAX-ACCESS   read-only
        STATUS       current
        DESCRIPTION  "SFP RX Power Status"
        ::= { meteringSfpEntry 6 }

-----------------------------------------------
-- pmonGroup Definitions
-----------------------------------------------

    pmon15minDataRadioGroup OBJECT IDENTIFIER
        ::= { pmonGroup 1 }

    pmon15minDataRadio2Table OBJECT-TYPE
        SYNTAX       SEQUENCE OF Pmon15minDataRadio2Entry
        MAX-ACCESS   not-accessible
        STATUS       current
        DESCRIPTION  "PMON MODEM 15min RF Monitoring Table (High Capacity)"
        ::= { pmon15minDataRadioGroup 2 }

    pmon15minDataRadio2Entry OBJECT-TYPE
        SYNTAX       Pmon15minDataRadio2Entry
        MAX-ACCESS   not-accessible
        STATUS       current
        DESCRIPTION  ""
        INDEX        {
                         pmon15minDataModem2IfIndex,
                         pmon15minDataModem2MonitorName
                     }
        ::= { pmon15minDataRadio2Table 1 }

    Pmon15minDataRadio2Entry ::= SEQUENCE {
        pmon15minDataModem2IfIndex      InterfaceIndex,
        pmon15minDataModem2MonitorName  INTEGER,
        pmon15minDataRadio2NEAddress    IpAddress,
        pmon15minDataModem2StatusInfo   IpeStatsInfo,
        pmon15minData2RfValue           IpeUnsigned64
    }

    pmon15minDataModem2IfIndex OBJECT-TYPE
        SYNTAX       InterfaceIndex
        MAX-ACCESS   not-accessible
        STATUS       current
        DESCRIPTION  "Index of this table."
        ::= { pmon15minDataRadio2Entry 1 }

    pmon15minDataModem2MonitorName OBJECT-TYPE
        SYNTAX       INTEGER {
                         pmonBBE(1),
                         pmonES(2),
                         pmonSES(3),
                         pmonSEF(4),
                         pmonUAS(5),
                         pmonOFS(6)
                     }
        MAX-ACCESS   not-accessible
        STATUS       current
        DESCRIPTION  
            "Index of this table. The value represents the monitoring item."
        ::= { pmon15minDataRadio2Entry 2 }

    pmon15minDataRadio2NEAddress OBJECT-TYPE
        SYNTAX       IpAddress
        MAX-ACCESS   not-accessible
        STATUS       current
        DESCRIPTION  "reserved."
        ::= { pmon15minDataRadio2Entry 3 }

    pmon15minDataModem2StatusInfo OBJECT-TYPE
        SYNTAX       IpeStatsInfo
        MAX-ACCESS   read-only
        STATUS       current
        DESCRIPTION  "PMON MODEM 15min RF Monitoring Status"
        ::= { pmon15minDataRadio2Entry 4 }

    pmon15minData2RfValue OBJECT-TYPE
        SYNTAX       IpeUnsigned64
        MAX-ACCESS   read-only
        STATUS       current
        DESCRIPTION  "PMON MODEM 15min RF Monitoring Value (High Capacity)"
        ::= { pmon15minDataRadio2Entry 5 }

    pmon1dayDataRadioGroup OBJECT IDENTIFIER
        ::= { pmonGroup 3 }

    pmon1dayDataRadio2Table OBJECT-TYPE
        SYNTAX       SEQUENCE OF Pmon1dayDataRadio2Entry
        MAX-ACCESS   not-accessible
        STATUS       current
        DESCRIPTION  "PMON MODEM 1day RF Monitoring Table (High Capacity)"
        ::= { pmon1dayDataRadioGroup 2 }

    pmon1dayDataRadio2Entry OBJECT-TYPE
        SYNTAX       Pmon1dayDataRadio2Entry
        MAX-ACCESS   not-accessible
        STATUS       current
        DESCRIPTION  ""
        INDEX        {
                         pmon1dayDataModem2IfIndex,
                         pmon1dayDataModem2MonitorName
                     }
        ::= { pmon1dayDataRadio2Table 1 }

    Pmon1dayDataRadio2Entry ::= SEQUENCE {
        pmon1dayDataModem2IfIndex      InterfaceIndex,
        pmon1dayDataModem2MonitorName  INTEGER,
        pmon1dayDataRadio2NEAddress    IpAddress,
        pmon1dayDataModem2StatusInfo   IpeStatsInfo,
        pmon1dayData2RfValue           IpeUnsigned64
    }

    pmon1dayDataModem2IfIndex OBJECT-TYPE
        SYNTAX       InterfaceIndex
        MAX-ACCESS   not-accessible
        STATUS       current
        DESCRIPTION  "Index of this table."
        ::= { pmon1dayDataRadio2Entry 1 }

    pmon1dayDataModem2MonitorName OBJECT-TYPE
        SYNTAX       INTEGER {
                         pmonBBE(1),
                         pmonES(2),
                         pmonSES(3),
                         pmonSEF(4),
                         pmonUAS(5),
                         pmonOFS(6)
                     }
        MAX-ACCESS   not-accessible
        STATUS       current
        DESCRIPTION  
            "Index of this table. The value represents the monitoring item."
        ::= { pmon1dayDataRadio2Entry 2 }

    pmon1dayDataRadio2NEAddress OBJECT-TYPE
        SYNTAX       IpAddress
        MAX-ACCESS   not-accessible
        STATUS       current
        DESCRIPTION  "reserved."
        ::= { pmon1dayDataRadio2Entry 3 }

    pmon1dayDataModem2StatusInfo OBJECT-TYPE
        SYNTAX       IpeStatsInfo
        MAX-ACCESS   read-only
        STATUS       current
        DESCRIPTION  "PMON MODEM 1day RF Monitoring Status"
        ::= { pmon1dayDataRadio2Entry 4 }

    pmon1dayData2RfValue OBJECT-TYPE
        SYNTAX       IpeUnsigned64
        MAX-ACCESS   read-only
        STATUS       current
        DESCRIPTION  "PMON MODEM 1day RF Monitoring Value (High Capacity)"
        ::= { pmon1dayDataRadio2Entry 5 }

    pmon15minDataModulationGroup OBJECT IDENTIFIER
        ::= { pmonGroup 5 }

    pmon15minModulationDataTable OBJECT-TYPE
        SYNTAX       SEQUENCE OF Pmon15minModulationDataEntry
        MAX-ACCESS   not-accessible
        STATUS       current
        DESCRIPTION  "15minutes Monitoring Table"
        ::= { pmon15minDataModulationGroup 1 }

    pmon15minModulationDataEntry OBJECT-TYPE
        SYNTAX       Pmon15minModulationDataEntry
        MAX-ACCESS   not-accessible
        STATUS       current
        DESCRIPTION  ""
        INDEX        { pmon15minModulationDataIfIndex }
        ::= { pmon15minModulationDataTable 1 }

    Pmon15minModulationDataEntry ::= SEQUENCE {
        pmon15minModulationDataIfIndex       InterfaceIndex,
        pmon15minModulationDataNEAddress     IpAddress,
        pmon15minTxModulationDataStatusInfo  IpeStatsInfo,
        pmon15minTxModulationData            INTEGER,
        pmon15minRxModulationDataStatusInfo  IpeStatsInfo,
        pmon15minRxModulationData            INTEGER
    }

    pmon15minModulationDataIfIndex OBJECT-TYPE
        SYNTAX       InterfaceIndex
        MAX-ACCESS   not-accessible
        STATUS       current
        DESCRIPTION  "Index of this table."
        ::= { pmon15minModulationDataEntry 1 }

    pmon15minModulationDataNEAddress OBJECT-TYPE
        SYNTAX       IpAddress
        MAX-ACCESS   not-accessible
        STATUS       current
        DESCRIPTION  "reserved"
        ::= { pmon15minModulationDataEntry 2 }

    pmon15minTxModulationDataStatusInfo OBJECT-TYPE
        SYNTAX       IpeStatsInfo
        MAX-ACCESS   read-only
        STATUS       current
        DESCRIPTION  "15minutes Tx Modulation."
        ::= { pmon15minModulationDataEntry 3 }

    pmon15minTxModulationData OBJECT-TYPE
        SYNTAX       INTEGER {
                         invalid(0),
                         qpsk(1),
                         qam16(2),
                         qam32(3),
                         qam64(4),
                         qam128(5),
                         qam256(6),
                         qam512(7),
                         qam1024(8),
                         psk8(11),
                         qpskOneFourthsBW(15),
                         qpskOneHalfBW(16)
                     }
        MAX-ACCESS   read-only
        STATUS       current
        DESCRIPTION  "15minutes Tx Modulation Status."
        ::= { pmon15minModulationDataEntry 4 }

    pmon15minRxModulationDataStatusInfo OBJECT-TYPE
        SYNTAX       IpeStatsInfo
        MAX-ACCESS   read-only
        STATUS       current
        DESCRIPTION  "15minutes Rx Modulation."
        ::= { pmon15minModulationDataEntry 5 }

    pmon15minRxModulationData OBJECT-TYPE
        SYNTAX       INTEGER {
                         invalid(0),
                         qpsk(1),
                         qam16(2),
                         qam32(3),
                         qam64(4),
                         qam128(5),
                         qam256(6),
                         qam512(7),
                         qam1024(8),
                         psk8(11),
                         qpskOneFourthsBW(15),
                         qpskOneHalfBW(16)
                     }
        MAX-ACCESS   read-only
        STATUS       current
        DESCRIPTION  "15minutes Rx Modulation Status."
        ::= { pmon15minModulationDataEntry 6 }

    pmon1dayDataModulationGroup OBJECT IDENTIFIER
        ::= { pmonGroup 6 }

    pmon1dayModulationDataTable OBJECT-TYPE
        SYNTAX       SEQUENCE OF Pmon1dayModulationDataEntry
        MAX-ACCESS   not-accessible
        STATUS       current
        DESCRIPTION  "1day Monitoring Table"
        ::= { pmon1dayDataModulationGroup 2 }

    pmon1dayModulationDataEntry OBJECT-TYPE
        SYNTAX       Pmon1dayModulationDataEntry
        MAX-ACCESS   not-accessible
        STATUS       current
        DESCRIPTION  ""
        INDEX        { pmon1dayModulationDataIfIndex }
        ::= { pmon1dayModulationDataTable 1 }

    Pmon1dayModulationDataEntry ::= SEQUENCE {
        pmon1dayModulationDataIfIndex       InterfaceIndex,
        pmon1dayModulationDataNEAddress     IpAddress,
        pmon1dayTxModulationDataStatusInfo  IpeStatsInfo,
        pmon1dayTxModulationData            INTEGER,
        pmon1dayRxModulationDataStatusInfo  IpeStatsInfo,
        pmon1dayRxModulationData            INTEGER
    }

    pmon1dayModulationDataIfIndex OBJECT-TYPE
        SYNTAX       InterfaceIndex
        MAX-ACCESS   not-accessible
        STATUS       current
        DESCRIPTION  "Index of this table."
        ::= { pmon1dayModulationDataEntry 1 }

    pmon1dayModulationDataNEAddress OBJECT-TYPE
        SYNTAX       IpAddress
        MAX-ACCESS   not-accessible
        STATUS       current
        DESCRIPTION  "reserved"
        ::= { pmon1dayModulationDataEntry 2 }

    pmon1dayTxModulationDataStatusInfo OBJECT-TYPE
        SYNTAX       IpeStatsInfo
        MAX-ACCESS   read-only
        STATUS       current
        DESCRIPTION  "1day Tx Modulation."
        ::= { pmon1dayModulationDataEntry 3 }

    pmon1dayTxModulationData OBJECT-TYPE
        SYNTAX       INTEGER {
                         invalid(0),
                         qpsk(1),
                         qam16(2),
                         qam32(3),
                         qam64(4),
                         qam128(5),
                         qam256(6),
                         qam512(7),
                         qam1024(8),
                         psk8(11),
                         qpskOneFourthsBW(15),
                         qpskOneHalfBW(16)
                     }
        MAX-ACCESS   read-only
        STATUS       current
        DESCRIPTION  "1day Tx Modulation Status."
        ::= { pmon1dayModulationDataEntry 4 }

    pmon1dayRxModulationDataStatusInfo OBJECT-TYPE
        SYNTAX       IpeStatsInfo
        MAX-ACCESS   read-only
        STATUS       current
        DESCRIPTION  "1day Rx Modulation."
        ::= { pmon1dayModulationDataEntry 5 }

    pmon1dayRxModulationData OBJECT-TYPE
        SYNTAX       INTEGER {
                         invalid(0),
                         qpsk(1),
                         qam16(2),
                         qam32(3),
                         qam64(4),
                         qam128(5),
                         qam256(6),
                         qam512(7),
                         qam1024(8),
                         psk8(11),
                         qpskOneFourthsBW(15),
                         qpskOneHalfBW(16)
                     }
        MAX-ACCESS   read-only
        STATUS       current
        DESCRIPTION  "1day Rx Modulation Status."
        ::= { pmon1dayModulationDataEntry 6 }

    pmonTxRxLev15minCurrentDataTable OBJECT-TYPE
        SYNTAX       SEQUENCE OF PmonTxRxLev15minCurrentDataEntry
        MAX-ACCESS   not-accessible
        STATUS       current
        DESCRIPTION  "PMON ODU 15min Tx/RX Level Monitoring Table"
        ::= { pmonTxRxLevGroup 1 }

    pmonTxRxLev15minCurrentDataEntry OBJECT-TYPE
        SYNTAX       PmonTxRxLev15minCurrentDataEntry
        MAX-ACCESS   not-accessible
        STATUS       current
        DESCRIPTION  ""
        INDEX        { pmonTxRxLev15minCurrentDataIfIndex }
        ::= { pmonTxRxLev15minCurrentDataTable 1 }

    PmonTxRxLev15minCurrentDataEntry ::= SEQUENCE {
        pmonTxRxLev15minCurrentDataIfIndex            InterfaceIndex,
        pmonTxRxLev15minCurrentDataNEAddress          IpAddress,
        pmonTxRxLev15minCurrentDataStatusInfo         IpeStatsInfo,
        pmonTxRxLev15minRxLevelMaxCurrentData         DisplayString,
        pmonTxRxLev15minRxLevelMinCurrentData         DisplayString,
        pmonTxRxLev15minTxLevelCurrentDataStatusInfo  IpeStatsInfo,
        pmonTxRxLev15minTxLevelMaxCurrentData         DisplayString,
        pmonTxRxLev15minTxLevelMinCurrentData         DisplayString
    }

    pmonTxRxLev15minCurrentDataIfIndex OBJECT-TYPE
        SYNTAX       InterfaceIndex
        MAX-ACCESS   not-accessible
        STATUS       current
        DESCRIPTION  "Index of this table."
        ::= { pmonTxRxLev15minCurrentDataEntry 1 }

    pmonTxRxLev15minCurrentDataNEAddress OBJECT-TYPE
        SYNTAX       IpAddress
        MAX-ACCESS   not-accessible
        STATUS       current
        DESCRIPTION  "reserved"
        ::= { pmonTxRxLev15minCurrentDataEntry 2 }

    pmonTxRxLev15minCurrentDataStatusInfo OBJECT-TYPE
        SYNTAX       IpeStatsInfo
        MAX-ACCESS   read-only
        STATUS       current
        DESCRIPTION  "PMON ODU 15min RX Level Status"
        ::= { pmonTxRxLev15minCurrentDataEntry 3 }

    pmonTxRxLev15minRxLevelMaxCurrentData OBJECT-TYPE
        SYNTAX       DisplayString
        MAX-ACCESS   read-only
        STATUS       current
        DESCRIPTION  "PMON ODU 15min RX Level (MAX)"
        ::= { pmonTxRxLev15minCurrentDataEntry 4 }

    pmonTxRxLev15minRxLevelMinCurrentData OBJECT-TYPE
        SYNTAX       DisplayString
        MAX-ACCESS   read-only
        STATUS       current
        DESCRIPTION  "PMON ODU 15min RX Level (MIN)"
        ::= { pmonTxRxLev15minCurrentDataEntry 5 }

    pmonTxRxLev15minTxLevelCurrentDataStatusInfo OBJECT-TYPE
        SYNTAX       IpeStatsInfo
        MAX-ACCESS   read-only
        STATUS       current
        DESCRIPTION  "PMON ODU 15min TX Level Status"
        ::= { pmonTxRxLev15minCurrentDataEntry 6 }

    pmonTxRxLev15minTxLevelMaxCurrentData OBJECT-TYPE
        SYNTAX       DisplayString
        MAX-ACCESS   read-only
        STATUS       current
        DESCRIPTION  "PMON ODU 15min TX Level (MAX)"
        ::= { pmonTxRxLev15minCurrentDataEntry 7 }

    pmonTxRxLev15minTxLevelMinCurrentData OBJECT-TYPE
        SYNTAX       DisplayString
        MAX-ACCESS   read-only
        STATUS       current
        DESCRIPTION  "PMON ODU 15min TX Level (MIN)"
        ::= { pmonTxRxLev15minCurrentDataEntry 8 }

    pmonTxRxLev1dayCurrentDataTable OBJECT-TYPE
        SYNTAX       SEQUENCE OF PmonTxRxLev1dayCurrentDataEntry
        MAX-ACCESS   not-accessible
        STATUS       current
        DESCRIPTION  "PMON ODU 1day Tx/RX Level Monitoring Table"
        ::= { pmonTxRxLevGroup 2 }

    pmonTxRxLev1dayCurrentDataEntry OBJECT-TYPE
        SYNTAX       PmonTxRxLev1dayCurrentDataEntry
        MAX-ACCESS   not-accessible
        STATUS       current
        DESCRIPTION  ""
        INDEX        { pmonTxRxLev1dayCurrentDataIfIndex }
        ::= { pmonTxRxLev1dayCurrentDataTable 1 }

    PmonTxRxLev1dayCurrentDataEntry ::= SEQUENCE {
        pmonTxRxLev1dayCurrentDataIfIndex            InterfaceIndex,
        pmonTxRxLev1dayCurrentDataNEAddress          IpAddress,
        pmonTxRxLev1dayCurrentDataStatusInfo         IpeStatsInfo,
        pmonTxRxLev1dayRxLevelMaxCurrentData         DisplayString,
        pmonTxRxLev1dayRxLevelMinCurrentData         DisplayString,
        pmonTxRxLev1dayTxLevelCurrentDataStatusInfo  IpeStatsInfo,
        pmonTxRxLev1dayTxLevelMaxCurrentData         DisplayString,
        pmonTxRxLev1dayTxLevelMinCurrentData         DisplayString
    }

    pmonTxRxLev1dayCurrentDataIfIndex OBJECT-TYPE
        SYNTAX       InterfaceIndex
        MAX-ACCESS   not-accessible
        STATUS       current
        DESCRIPTION  "Index of this table."
        ::= { pmonTxRxLev1dayCurrentDataEntry 1 }

    pmonTxRxLev1dayCurrentDataNEAddress OBJECT-TYPE
        SYNTAX       IpAddress
        MAX-ACCESS   not-accessible
        STATUS       current
        DESCRIPTION  "reserved"
        ::= { pmonTxRxLev1dayCurrentDataEntry 2 }

    pmonTxRxLev1dayCurrentDataStatusInfo OBJECT-TYPE
        SYNTAX       IpeStatsInfo
        MAX-ACCESS   read-only
        STATUS       current
        DESCRIPTION  "PMON ODU 1day RX Level Status"
        ::= { pmonTxRxLev1dayCurrentDataEntry 3 }

    pmonTxRxLev1dayRxLevelMaxCurrentData OBJECT-TYPE
        SYNTAX       DisplayString
        MAX-ACCESS   read-only
        STATUS       current
        DESCRIPTION  "PMON ODU 1day RX Level (MAX)"
        ::= { pmonTxRxLev1dayCurrentDataEntry 4 }

    pmonTxRxLev1dayRxLevelMinCurrentData OBJECT-TYPE
        SYNTAX       DisplayString
        MAX-ACCESS   read-only
        STATUS       current
        DESCRIPTION  "PMON ODU 1day RX Level (MIN)"
        ::= { pmonTxRxLev1dayCurrentDataEntry 5 }

    pmonTxRxLev1dayTxLevelCurrentDataStatusInfo OBJECT-TYPE
        SYNTAX       IpeStatsInfo
        MAX-ACCESS   read-only
        STATUS       current
        DESCRIPTION  "PMON ODU 1day TX Level Status"
        ::= { pmonTxRxLev1dayCurrentDataEntry 6 }

    pmonTxRxLev1dayTxLevelMaxCurrentData OBJECT-TYPE
        SYNTAX       DisplayString
        MAX-ACCESS   read-only
        STATUS       current
        DESCRIPTION  "PMON ODU 1day TX Level (MAX)"
        ::= { pmonTxRxLev1dayCurrentDataEntry 7 }

    pmonTxRxLev1dayTxLevelMinCurrentData OBJECT-TYPE
        SYNTAX       DisplayString
        MAX-ACCESS   read-only
        STATUS       current
        DESCRIPTION  "PMON ODU 1day TX Level (MIN)"
        ::= { pmonTxRxLev1dayCurrentDataEntry 8 }

-----------------------------------------------
-- rmonGroup Definitions
-----------------------------------------------

    rmonEthGroup OBJECT IDENTIFIER
        ::= { rmonGroup 1 }

    rmon15minPortGroup OBJECT IDENTIFIER
        ::= { rmonEthGroup 1 }

    rmon15minPort2Table OBJECT-TYPE
        SYNTAX       SEQUENCE OF Rmon15minPort2Entry
        MAX-ACCESS   not-accessible
        STATUS       current
        DESCRIPTION  "RMON 15min Port Monitoring Table."
        ::= { rmon15minPortGroup 2 }

    rmon15minPort2Entry OBJECT-TYPE
        SYNTAX       Rmon15minPort2Entry
        MAX-ACCESS   not-accessible
        STATUS       current
        DESCRIPTION  ""
        INDEX        { rmon15minPort2IfIndex }
        ::= { rmon15minPort2Table 1 }

    Rmon15minPort2Entry ::= SEQUENCE {
        rmon15minPort2IfIndex                             InterfaceIndex,
        rmon15minPort2NEAddress                           IpAddress,
        rmon15minHCRxEthStatsOctets2                      Counter64,
        rmon15minHCRxEthStatsOctets2Status                IpeStatsInfo,
        rmon15minHCTxEthStatsOctets2                      Counter64,
        rmon15minHCTxEthStatsOctets2Status                IpeStatsInfo,
        rmon15minHCRxEthStatsPkts2                        Counter64,
        rmon15minHCRxEthStatsPkts2Status                  IpeStatsInfo,
        rmon15minHCTxEthStatsPkts2                        Counter64,
        rmon15minHCTxEthStatsPkts2Status                  IpeStatsInfo,
        rmon15minRxEthStatsDropEvents2                    Counter32,
        rmon15minRxEthStatsDropEvents2Status              IpeStatsInfo,
        rmon15minRxEthStatsUndersizePkts2                 Counter32,
        rmon15minRxEthStatsUndersizePkts2Status           IpeStatsInfo,
        rmon15minRxEthStatsFragments2                     Counter32,
        rmon15minRxEthStatsFragments2Status               IpeStatsInfo,
        rmon15minHCRxEthStatsPkts64Octets2                Counter64,
        rmon15minHCRxEthStatsPkts64Octets2Status          IpeStatsInfo,
        rmon15minHCTxEthStatsPkts64Octets2                Counter64,
        rmon15minHCTxEthStatsPkts64Octets2Status          IpeStatsInfo,
        rmon15minHCRxEthStatsPkts65to127Octets2           Counter64,
        rmon15minHCRxEthStatsPkts65to127Octets2Status     IpeStatsInfo,
        rmon15minHCTxEthStatsPkts65to127Octets2           Counter64,
        rmon15minHCTxEthStatsPkts65to127Octets2Status     IpeStatsInfo,
        rmon15minHCRxEthStatsPkts128to255Octets2          Counter64,
        rmon15minHCRxEthStatsPkts128to255Octets2Status    IpeStatsInfo,
        rmon15minHCTxEthStatsPkts128to255Octets2          Counter64,
        rmon15minHCTxEthStatsPkts128to255Octets2Status    IpeStatsInfo,
        rmon15minHCRxEthStatsPkts256to511Octets2          Counter64,
        rmon15minHCRxEthStatsPkts256to511Octets2Status    IpeStatsInfo,
        rmon15minHCTxEthStatsPkts256to511Octets2          Counter64,
        rmon15minHCTxEthStatsPkts256to511Octets2Status    IpeStatsInfo,
        rmon15minHCRxEthStatsPkts512to1023Octets2         Counter64,
        rmon15minHCRxEthStatsPkts512to1023Octets2Status   IpeStatsInfo,
        rmon15minHCTxEthStatsPkts512to1023Octets2         Counter64,
        rmon15minHCTxEthStatsPkts512to1023Octets2Status   IpeStatsInfo,
        rmon15minHCRxEthStatsPkts1024to1518Octets2        Counter64,
        rmon15minHCRxEthStatsPkts1024to1518Octets2Status  IpeStatsInfo,
        rmon15minHCTxEthStatsPkts1024to1518Octets2        Counter64,
        rmon15minHCTxEthStatsPkts1024to1518Octets2Status  IpeStatsInfo,
        rmon15minRxEthStatsCRCAlignErrors2                Counter32,
        rmon15minRxEthStatsCRCAlignErrors2Status          IpeStatsInfo,
        rmon15minRxEthStatsOversizePkts2                  Counter32,
        rmon15minRxEthStatsOversizePkts2Status            IpeStatsInfo,
        rmon15minRxEthStatsJabbers2                       Counter32,
        rmon15minRxEthStatsJabbers2Status                 IpeStatsInfo,
        rmon15minRxEthStatsMulticastPkts2                 Counter32,
        rmon15minRxEthStatsMulticastPkts2Status           IpeStatsInfo,
        rmon15minTxEthStatsMulticastPkts2                 Counter32,
        rmon15minTxEthStatsMulticastPkts2Status           IpeStatsInfo,
        rmon15minRxEthStatsBroadcastPkts2                 Counter32,
        rmon15minRxEthStatsBroadcastPkts2Status           IpeStatsInfo,
        rmon15minTxEthStatsBroadcastPkts2                 Counter32,
        rmon15minTxEthStatsBroadcastPkts2Status           IpeStatsInfo,
        rmon15minTxEthStatsCollisions2                    Counter32,
        rmon15minTxEthStatsCollisions2Status              IpeStatsInfo,
        rmon15minHCRxUnknownTPID2                         Counter64,
        rmon15minHCRxUnknownTPID2Status                   IpeStatsInfo,
        rmon15minHCRxUnknownVID2                          Counter64,
        rmon15minHCRxUnknownVID2Status                    IpeStatsInfo,
        rmon15minHCRxMAClimit2                            Counter64,
        rmon15minHCRxMAClimit2Status                      IpeStatsInfo,
        rmon15minHCRxFilterDiscard2                       Counter64,
        rmon15minHCRxFilterDiscard2Status                 IpeStatsInfo,
        rmon15minHCRxQoSDiscard2                          Counter64,
        rmon15minHCRxQoSDiscard2Status                    IpeStatsInfo,
        rmon15minHCTxQueue0Discard2                       Counter64,
        rmon15minHCTxQueue0Discard2Status                 IpeStatsInfo,
        rmon15minHCTxQueue1Discard2                       Counter64,
        rmon15minHCTxQueue1Discard2Status                 IpeStatsInfo,
        rmon15minHCTxQueue2Discard2                       Counter64,
        rmon15minHCTxQueue2Discard2Status                 IpeStatsInfo,
        rmon15minHCTxQueue3Discard2                       Counter64,
        rmon15minHCTxQueue3Discard2Status                 IpeStatsInfo,
        rmon15minHCTxQueue4Discard2                       Counter64,
        rmon15minHCTxQueue4Discard2Status                 IpeStatsInfo,
        rmon15minHCTxQueue5Discard2                       Counter64,
        rmon15minHCTxQueue5Discard2Status                 IpeStatsInfo,
        rmon15minHCTxQueue6Discard2                       Counter64,
        rmon15minHCTxQueue6Discard2Status                 IpeStatsInfo,
        rmon15minHCTxQueue7Discard2                       Counter64,
        rmon15minHCTxQueue7Discard2Status                 IpeStatsInfo,
        rmon15minTxEthStatsOversizePkts2                  Counter32,
        rmon15minTxEthStatsOversizePkts2Status            IpeStatsInfo,
        rmon15minHCTxFilterDiscard2                       Counter64,
        rmon15minHCTxFilterDiscard2Status                 IpeStatsInfo
    }

    rmon15minPort2IfIndex OBJECT-TYPE
        SYNTAX       InterfaceIndex
        MAX-ACCESS   not-accessible
        STATUS       current
        DESCRIPTION  "Index of this table."
        ::= { rmon15minPort2Entry 1 }

    rmon15minPort2NEAddress OBJECT-TYPE
        SYNTAX       IpAddress
        MAX-ACCESS   not-accessible
        STATUS       current
        DESCRIPTION  "reserved."
        ::= { rmon15minPort2Entry 2 }

    rmon15minHCRxEthStatsOctets2 OBJECT-TYPE
        SYNTAX       Counter64
        MAX-ACCESS   read-only
        STATUS       current
        DESCRIPTION  "RMON 15min RX Octs"
        ::= { rmon15minPort2Entry 3 }

    rmon15minHCRxEthStatsOctets2Status OBJECT-TYPE
        SYNTAX       IpeStatsInfo
        MAX-ACCESS   read-only
        STATUS       current
        DESCRIPTION  
            "RMON 15min RX Octs Status. 'invalid' means the corresponding
            monitoring value is not reliable because of the alarm or other
            reasons. 'maintenance' means that some maintenance functions are
            executed on the current interval."
        ::= { rmon15minPort2Entry 4 }

    rmon15minHCTxEthStatsOctets2 OBJECT-TYPE
        SYNTAX       Counter64
        MAX-ACCESS   read-only
        STATUS       current
        DESCRIPTION  "RMON 15min TX Octs"
        ::= { rmon15minPort2Entry 5 }

    rmon15minHCTxEthStatsOctets2Status OBJECT-TYPE
        SYNTAX       IpeStatsInfo
        MAX-ACCESS   read-only
        STATUS       current
        DESCRIPTION  
            "RMON 15min TX Octs Status. 'invalid' means the corresponding
            monitoring value is not reliable because of the alarm or other
            reasons. 'maintenance' means that some maintenance functions are
            executed on the current interval."
        ::= { rmon15minPort2Entry 6 }

    rmon15minHCRxEthStatsPkts2 OBJECT-TYPE
        SYNTAX       Counter64
        MAX-ACCESS   read-only
        STATUS       current
        DESCRIPTION  "RMON 15min RX Pkts"
        ::= { rmon15minPort2Entry 7 }

    rmon15minHCRxEthStatsPkts2Status OBJECT-TYPE
        SYNTAX       IpeStatsInfo
        MAX-ACCESS   read-only
        STATUS       current
        DESCRIPTION  
            "RMON 15min RX Pkts Status. 'invalid' means the corresponding
            monitoring value is not reliable because of the alarm or other
            reasons. 'maintenance' means that some maintenance functions are
            executed on the current interval."
        ::= { rmon15minPort2Entry 8 }

    rmon15minHCTxEthStatsPkts2 OBJECT-TYPE
        SYNTAX       Counter64
        MAX-ACCESS   read-only
        STATUS       current
        DESCRIPTION  "RMON 15min TX Pkts"
        ::= { rmon15minPort2Entry 9 }

    rmon15minHCTxEthStatsPkts2Status OBJECT-TYPE
        SYNTAX       IpeStatsInfo
        MAX-ACCESS   read-only
        STATUS       current
        DESCRIPTION  
            "RMON 15min TX Pkts Status. 'invalid' means the corresponding
            monitoring value is not reliable because of the alarm or other
            reasons. 'maintenance' means that some maintenance functions are
            executed on the current interval."
        ::= { rmon15minPort2Entry 10 }

    rmon15minRxEthStatsDropEvents2 OBJECT-TYPE
        SYNTAX       Counter32
        MAX-ACCESS   read-only
        STATUS       current
        DESCRIPTION  "RMON 15min RX Drop Events"
        ::= { rmon15minPort2Entry 11 }

    rmon15minRxEthStatsDropEvents2Status OBJECT-TYPE
        SYNTAX       IpeStatsInfo
        MAX-ACCESS   read-only
        STATUS       current
        DESCRIPTION  
            "RMON 15min RX Drop Events Status. 'invalid' means the
            corresponding monitoring value is not reliable because of the
            alarm or other reasons. 'maintenance' means that some maintenance
            functions are executed on the current interval."
        ::= { rmon15minPort2Entry 12 }

    rmon15minRxEthStatsUndersizePkts2 OBJECT-TYPE
        SYNTAX       Counter32
        MAX-ACCESS   read-only
        STATUS       current
        DESCRIPTION  "RMON 15min RX Undersize Pkts"
        ::= { rmon15minPort2Entry 13 }

    rmon15minRxEthStatsUndersizePkts2Status OBJECT-TYPE
        SYNTAX       IpeStatsInfo
        MAX-ACCESS   read-only
        STATUS       current
        DESCRIPTION  
            "RMON 15min RX Undersize Pkts Status. 'invalid' means the
            corresponding monitoring value is not reliable because of the
            alarm or other reasons. 'maintenance' means that some maintenance
            functions are executed on the current interval."
        ::= { rmon15minPort2Entry 14 }

    rmon15minRxEthStatsFragments2 OBJECT-TYPE
        SYNTAX       Counter32
        MAX-ACCESS   read-only
        STATUS       current
        DESCRIPTION  "RMON 15min RX Fragments"
        ::= { rmon15minPort2Entry 15 }

    rmon15minRxEthStatsFragments2Status OBJECT-TYPE
        SYNTAX       IpeStatsInfo
        MAX-ACCESS   read-only
        STATUS       current
        DESCRIPTION  
            "RMON 15min RX Fragments Status. 'invalid' means the
            corresponding monitoring value is not reliable because of the
            alarm or other reasons. 'maintenance' means that some maintenance
            functions are executed on the current interval."
        ::= { rmon15minPort2Entry 16 }

    rmon15minHCRxEthStatsPkts64Octets2 OBJECT-TYPE
        SYNTAX       Counter64
        MAX-ACCESS   read-only
        STATUS       current
        DESCRIPTION  "RMON 15min RX 64 Octs"
        ::= { rmon15minPort2Entry 17 }

    rmon15minHCRxEthStatsPkts64Octets2Status OBJECT-TYPE
        SYNTAX       IpeStatsInfo
        MAX-ACCESS   read-only
        STATUS       current
        DESCRIPTION  
            "RMON 15min RX 64 Octs Status. 'invalid' means the corresponding
            monitoring value is not reliable because of the alarm or other
            reasons. 'maintenance' means that some maintenance functions are
            executed on the current interval."
        ::= { rmon15minPort2Entry 18 }

    rmon15minHCTxEthStatsPkts64Octets2 OBJECT-TYPE
        SYNTAX       Counter64
        MAX-ACCESS   read-only
        STATUS       current
        DESCRIPTION  "RMON 15min TX 64 Octs"
        ::= { rmon15minPort2Entry 19 }

    rmon15minHCTxEthStatsPkts64Octets2Status OBJECT-TYPE
        SYNTAX       IpeStatsInfo
        MAX-ACCESS   read-only
        STATUS       current
        DESCRIPTION  
            "RMON 15min TX 64 Octs Status. 'invalid' means the corresponding
            monitoring value is not reliable because of the alarm or other
            reasons. 'maintenance' means that some maintenance functions are
            executed on the current interval."
        ::= { rmon15minPort2Entry 20 }

    rmon15minHCRxEthStatsPkts65to127Octets2 OBJECT-TYPE
        SYNTAX       Counter64
        MAX-ACCESS   read-only
        STATUS       current
        DESCRIPTION  "RMON 15min RX 65 to 127 Octs"
        ::= { rmon15minPort2Entry 21 }

    rmon15minHCRxEthStatsPkts65to127Octets2Status OBJECT-TYPE
        SYNTAX       IpeStatsInfo
        MAX-ACCESS   read-only
        STATUS       current
        DESCRIPTION  
            "RMON 15min RX 65 to 127 Octs Status. 'invalid' means the
            corresponding monitoring value is not reliable because of the
            alarm or other reasons. 'maintenance' means that some maintenance
            functions are executed on the current interval."
        ::= { rmon15minPort2Entry 22 }

    rmon15minHCTxEthStatsPkts65to127Octets2 OBJECT-TYPE
        SYNTAX       Counter64
        MAX-ACCESS   read-only
        STATUS       current
        DESCRIPTION  "RMON 15min TX 65 to 127 Octs"
        ::= { rmon15minPort2Entry 23 }

    rmon15minHCTxEthStatsPkts65to127Octets2Status OBJECT-TYPE
        SYNTAX       IpeStatsInfo
        MAX-ACCESS   read-only
        STATUS       current
        DESCRIPTION  
            "RMON 15min TX 65 to 127 Octs Status. 'invalid' means the
            corresponding monitoring value is not reliable because of the
            alarm or other reasons. 'maintenance' means that some maintenance
            functions are executed on the current interval."
        ::= { rmon15minPort2Entry 24 }

    rmon15minHCRxEthStatsPkts128to255Octets2 OBJECT-TYPE
        SYNTAX       Counter64
        MAX-ACCESS   read-only
        STATUS       current
        DESCRIPTION  "RMON 15min RX 128 to 255 Octs"
        ::= { rmon15minPort2Entry 25 }

    rmon15minHCRxEthStatsPkts128to255Octets2Status OBJECT-TYPE
        SYNTAX       IpeStatsInfo
        MAX-ACCESS   read-only
        STATUS       current
        DESCRIPTION  
            "RMON 15min RX 128 to 255 Octs Status. 'invalid' means the
            corresponding monitoring value is not reliable because of the
            alarm or other reasons. 'maintenance' means that some maintenance
            functions are executed on the current interval."
        ::= { rmon15minPort2Entry 26 }

    rmon15minHCTxEthStatsPkts128to255Octets2 OBJECT-TYPE
        SYNTAX       Counter64
        MAX-ACCESS   read-only
        STATUS       current
        DESCRIPTION  "RMON 15min TX 128 to 255 Octs"
        ::= { rmon15minPort2Entry 27 }

    rmon15minHCTxEthStatsPkts128to255Octets2Status OBJECT-TYPE
        SYNTAX       IpeStatsInfo
        MAX-ACCESS   read-only
        STATUS       current
        DESCRIPTION  
            "RMON 15min TX 128 to 255 Octs Status. 'invalid' means the
            corresponding monitoring value is not reliable because of the
            alarm or other reasons. 'maintenance' means that some maintenance
            functions are executed on the current interval."
        ::= { rmon15minPort2Entry 28 }

    rmon15minHCRxEthStatsPkts256to511Octets2 OBJECT-TYPE
        SYNTAX       Counter64
        MAX-ACCESS   read-only
        STATUS       current
        DESCRIPTION  "RMON 15min RX 256 to 511 Octs"
        ::= { rmon15minPort2Entry 29 }

    rmon15minHCRxEthStatsPkts256to511Octets2Status OBJECT-TYPE
        SYNTAX       IpeStatsInfo
        MAX-ACCESS   read-only
        STATUS       current
        DESCRIPTION  
            "RMON 15min RX 256 to 511 Octs Status. 'invalid' means the
            corresponding monitoring value is not reliable because of the
            alarm or other reasons. 'maintenance' means that some maintenance
            functions are executed on the current interval."
        ::= { rmon15minPort2Entry 30 }

    rmon15minHCTxEthStatsPkts256to511Octets2 OBJECT-TYPE
        SYNTAX       Counter64
        MAX-ACCESS   read-only
        STATUS       current
        DESCRIPTION  "RMON 15min TX 256 to 511 Octs"
        ::= { rmon15minPort2Entry 31 }

    rmon15minHCTxEthStatsPkts256to511Octets2Status OBJECT-TYPE
        SYNTAX       IpeStatsInfo
        MAX-ACCESS   read-only
        STATUS       current
        DESCRIPTION  
            "RMON 15min TX 256 to 511 Octs Status. 'invalid' means the
            corresponding monitoring value is not reliable because of the
            alarm or other reasons. 'maintenance' means that some maintenance
            functions are executed on the current interval."
        ::= { rmon15minPort2Entry 32 }

    rmon15minHCRxEthStatsPkts512to1023Octets2 OBJECT-TYPE
        SYNTAX       Counter64
        MAX-ACCESS   read-only
        STATUS       current
        DESCRIPTION  "RMON 15min RX 512 to 1023 Octs"
        ::= { rmon15minPort2Entry 33 }

    rmon15minHCRxEthStatsPkts512to1023Octets2Status OBJECT-TYPE
        SYNTAX       IpeStatsInfo
        MAX-ACCESS   read-only
        STATUS       current
        DESCRIPTION  
            "RMON 15min RX 512 to 1023 Octs Status. 'invalid' means the
            corresponding monitoring value is not reliable because of the
            alarm or other reasons. 'maintenance' means that some maintenance
            functions are executed on the current interval."
        ::= { rmon15minPort2Entry 34 }

    rmon15minHCTxEthStatsPkts512to1023Octets2 OBJECT-TYPE
        SYNTAX       Counter64
        MAX-ACCESS   read-only
        STATUS       current
        DESCRIPTION  "RMON 15min TX 512 to 1023 Octs"
        ::= { rmon15minPort2Entry 35 }

    rmon15minHCTxEthStatsPkts512to1023Octets2Status OBJECT-TYPE
        SYNTAX       IpeStatsInfo
        MAX-ACCESS   read-only
        STATUS       current
        DESCRIPTION  
            "RMON 15min TX 512 to 1023 Octs Status. 'invalid' means the
            corresponding monitoring value is not reliable because of the
            alarm or other reasons. 'maintenance' means that some maintenance
            functions are executed on the current interval."
        ::= { rmon15minPort2Entry 36 }

    rmon15minHCRxEthStatsPkts1024to1518Octets2 OBJECT-TYPE
        SYNTAX       Counter64
        MAX-ACCESS   read-only
        STATUS       current
        DESCRIPTION  "RMON 15min RX 1024 to 1518 Octs"
        ::= { rmon15minPort2Entry 37 }

    rmon15minHCRxEthStatsPkts1024to1518Octets2Status OBJECT-TYPE
        SYNTAX       IpeStatsInfo
        MAX-ACCESS   read-only
        STATUS       current
        DESCRIPTION  
            "RMON 15min RX 1024 to 1518 Octs Status. 'invalid' means the
            corresponding monitoring value is not reliable because of the
            alarm or other reasons. 'maintenance' means that some maintenance
            functions are executed on the current interval."
        ::= { rmon15minPort2Entry 38 }

    rmon15minHCTxEthStatsPkts1024to1518Octets2 OBJECT-TYPE
        SYNTAX       Counter64
        MAX-ACCESS   read-only
        STATUS       current
        DESCRIPTION  "RMON 15min TX 1024 to 1518 Octs"
        ::= { rmon15minPort2Entry 39 }

    rmon15minHCTxEthStatsPkts1024to1518Octets2Status OBJECT-TYPE
        SYNTAX       IpeStatsInfo
        MAX-ACCESS   read-only
        STATUS       current
        DESCRIPTION  
            "RMON 15min TX 1024 to 1518 Octs Status. 'invalid' means the
            corresponding monitoring value is not reliable because of the
            alarm or other reasons. 'maintenance' means that some maintenance
            functions are executed on the current interval."
        ::= { rmon15minPort2Entry 40 }

    rmon15minRxEthStatsCRCAlignErrors2 OBJECT-TYPE
        SYNTAX       Counter32
        MAX-ACCESS   read-only
        STATUS       current
        DESCRIPTION  "RMON 15min RX CRC Alignment Errors"
        ::= { rmon15minPort2Entry 41 }

    rmon15minRxEthStatsCRCAlignErrors2Status OBJECT-TYPE
        SYNTAX       IpeStatsInfo
        MAX-ACCESS   read-only
        STATUS       current
        DESCRIPTION  
            "RMON 15min RX CRC Alignment Errors Status. 'invalid' means the
            corresponding monitoring value is not reliable because of the
            alarm or other reasons. 'maintenance' means that some maintenance
            functions are executed on the current interval."
        ::= { rmon15minPort2Entry 42 }

    rmon15minRxEthStatsOversizePkts2 OBJECT-TYPE
        SYNTAX       Counter32
        MAX-ACCESS   read-only
        STATUS       current
        DESCRIPTION  "RMON 15min RX Oversize Pkts"
        ::= { rmon15minPort2Entry 43 }

    rmon15minRxEthStatsOversizePkts2Status OBJECT-TYPE
        SYNTAX       IpeStatsInfo
        MAX-ACCESS   read-only
        STATUS       current
        DESCRIPTION  
            "RMON 15min RX Oversize Pkts Status. 'invalid' means the
            corresponding monitoring value is not reliable because of the
            alarm or other reasons. 'maintenance' means that some maintenance
            functions are executed on the current interval."
        ::= { rmon15minPort2Entry 44 }

    rmon15minRxEthStatsJabbers2 OBJECT-TYPE
        SYNTAX       Counter32
        MAX-ACCESS   read-only
        STATUS       current
        DESCRIPTION  "RMON 15min RX Jabbers"
        ::= { rmon15minPort2Entry 45 }

    rmon15minRxEthStatsJabbers2Status OBJECT-TYPE
        SYNTAX       IpeStatsInfo
        MAX-ACCESS   read-only
        STATUS       current
        DESCRIPTION  
            "RMON 15min RX Jabbers Status. 'invalid' means the corresponding
            monitoring value is not reliable because of the alarm or other
            reasons. 'maintenance' means that some maintenance functions are
            executed on the current interval."
        ::= { rmon15minPort2Entry 46 }

    rmon15minRxEthStatsMulticastPkts2 OBJECT-TYPE
        SYNTAX       Counter32
        MAX-ACCESS   read-only
        STATUS       current
        DESCRIPTION  "RMON 15min RX Multicast Pkts"
        ::= { rmon15minPort2Entry 47 }

    rmon15minRxEthStatsMulticastPkts2Status OBJECT-TYPE
        SYNTAX       IpeStatsInfo
        MAX-ACCESS   read-only
        STATUS       current
        DESCRIPTION  
            "RMON 15min RX Multicast Pkts Status. 'invalid' means the
            corresponding monitoring value is not reliable because of the
            alarm or other reasons. 'maintenance' means that some maintenance
            functions are executed on the current interval."
        ::= { rmon15minPort2Entry 48 }

    rmon15minTxEthStatsMulticastPkts2 OBJECT-TYPE
        SYNTAX       Counter32
        MAX-ACCESS   read-only
        STATUS       current
        DESCRIPTION  "RMON 15min TX Multicast Pkts"
        ::= { rmon15minPort2Entry 49 }

    rmon15minTxEthStatsMulticastPkts2Status OBJECT-TYPE
        SYNTAX       IpeStatsInfo
        MAX-ACCESS   read-only
        STATUS       current
        DESCRIPTION  
            "RMON 15min TX Multicast Pkts Status. 'invalid' means the
            corresponding monitoring value is not reliable because of the
            alarm or other reasons. 'maintenance' means that some maintenance
            functions are executed on the current interval."
        ::= { rmon15minPort2Entry 50 }

    rmon15minRxEthStatsBroadcastPkts2 OBJECT-TYPE
        SYNTAX       Counter32
        MAX-ACCESS   read-only
        STATUS       current
        DESCRIPTION  "RMON 15min RX Broadcast Pkts"
        ::= { rmon15minPort2Entry 51 }

    rmon15minRxEthStatsBroadcastPkts2Status OBJECT-TYPE
        SYNTAX       IpeStatsInfo
        MAX-ACCESS   read-only
        STATUS       current
        DESCRIPTION  
            "RMON 15min RX Broadcast Pkts Status. 'invalid' means the
            corresponding monitoring value is not reliable because of the
            alarm or other reasons. 'maintenance' means that some maintenance
            functions are executed on the current interval."
        ::= { rmon15minPort2Entry 52 }

    rmon15minTxEthStatsBroadcastPkts2 OBJECT-TYPE
        SYNTAX       Counter32
        MAX-ACCESS   read-only
        STATUS       current
        DESCRIPTION  "RMON 15min TX Broadcast Pkts"
        ::= { rmon15minPort2Entry 53 }

    rmon15minTxEthStatsBroadcastPkts2Status OBJECT-TYPE
        SYNTAX       IpeStatsInfo
        MAX-ACCESS   read-only
        STATUS       current
        DESCRIPTION  
            "RMON 15min TX Broadcast Pkts Status. 'invalid' means the
            corresponding monitoring value is not reliable because of the
            alarm or other reasons. 'maintenance' means that some maintenance
            functions are executed on the current interval."
        ::= { rmon15minPort2Entry 54 }

    rmon15minTxEthStatsCollisions2 OBJECT-TYPE
        SYNTAX       Counter32
        MAX-ACCESS   read-only
        STATUS       current
        DESCRIPTION  "RMON 15min TX Collisions"
        ::= { rmon15minPort2Entry 55 }

    rmon15minTxEthStatsCollisions2Status OBJECT-TYPE
        SYNTAX       IpeStatsInfo
        MAX-ACCESS   read-only
        STATUS       current
        DESCRIPTION  
            "RMON 15min TX Collisions Status. 'invalid' means the
            corresponding monitoring value is not reliable because of the
            alarm or other reasons. 'maintenance' means that some maintenance
            functions are executed on the current interval."
        ::= { rmon15minPort2Entry 56 }

    rmon15minHCRxUnknownTPID2 OBJECT-TYPE
        SYNTAX       Counter64
        MAX-ACCESS   read-only
        STATUS       current
        DESCRIPTION  "RMON 15min Unknown TPID"
        ::= { rmon15minPort2Entry 57 }

    rmon15minHCRxUnknownTPID2Status OBJECT-TYPE
        SYNTAX       IpeStatsInfo
        MAX-ACCESS   read-only
        STATUS       current
        DESCRIPTION  
            "RMON 15min Unknown TPID Status. 'invalid' means the
            corresponding monitoring value is not reliable because of the
            alarm or other reasons. 'maintenance' means that some maintenance
            functions are executed on the current interval."
        ::= { rmon15minPort2Entry 58 }

    rmon15minHCRxUnknownVID2 OBJECT-TYPE
        SYNTAX       Counter64
        MAX-ACCESS   read-only
        STATUS       current
        DESCRIPTION  "RMON 15min Unknown VID"
        ::= { rmon15minPort2Entry 59 }

    rmon15minHCRxUnknownVID2Status OBJECT-TYPE
        SYNTAX       IpeStatsInfo
        MAX-ACCESS   read-only
        STATUS       current
        DESCRIPTION  
            "RMON 15min Unknown VID Status. 'invalid' means the corresponding
            monitoring value is not reliable because of the alarm or other
            reasons. 'maintenance' means that some maintenance functions are
            executed on the current interval."
        ::= { rmon15minPort2Entry 60 }

    rmon15minHCRxMAClimit2 OBJECT-TYPE
        SYNTAX       Counter64
        MAX-ACCESS   read-only
        STATUS       current
        DESCRIPTION  "RMON 15min RX MAC Limit"
        ::= { rmon15minPort2Entry 61 }

    rmon15minHCRxMAClimit2Status OBJECT-TYPE
        SYNTAX       IpeStatsInfo
        MAX-ACCESS   read-only
        STATUS       current
        DESCRIPTION  
            "RMON 15min RX MAC Limit Status. 'invalid' means the
            corresponding monitoring value is not reliable because of the
            alarm or other reasons. 'maintenance' means that some maintenance
            functions are executed on the current interval."
        ::= { rmon15minPort2Entry 62 }

    rmon15minHCRxFilterDiscard2 OBJECT-TYPE
        SYNTAX       Counter64
        MAX-ACCESS   read-only
        STATUS       current
        DESCRIPTION  "RMON 15min RX Filter Discard"
        ::= { rmon15minPort2Entry 63 }

    rmon15minHCRxFilterDiscard2Status OBJECT-TYPE
        SYNTAX       IpeStatsInfo
        MAX-ACCESS   read-only
        STATUS       current
        DESCRIPTION  
            "RMON 15min RX Filter Discard Status. 'invalid' means the
            corresponding monitoring value is not reliable because of the
            alarm or other reasons. 'maintenance' means that some maintenance
            functions are executed on the current interval."
        ::= { rmon15minPort2Entry 64 }

    rmon15minHCRxQoSDiscard2 OBJECT-TYPE
        SYNTAX       Counter64
        MAX-ACCESS   read-only
        STATUS       current
        DESCRIPTION  "RMON 15min RX QoS Discard"
        ::= { rmon15minPort2Entry 65 }

    rmon15minHCRxQoSDiscard2Status OBJECT-TYPE
        SYNTAX       IpeStatsInfo
        MAX-ACCESS   read-only
        STATUS       current
        DESCRIPTION  
            "RMON 15min RX QoS Discard Status. 'invalid' means the
            corresponding monitoring value is not reliable because of the
            alarm or other reasons. 'maintenance' means that some maintenance
            functions are executed on the current interval."
        ::= { rmon15minPort2Entry 66 }

    rmon15minHCTxQueue0Discard2 OBJECT-TYPE
        SYNTAX       Counter64
        MAX-ACCESS   read-only
        STATUS       current
        DESCRIPTION  "RMON 15min TX Queue0 Discard"
        ::= { rmon15minPort2Entry 67 }

    rmon15minHCTxQueue0Discard2Status OBJECT-TYPE
        SYNTAX       IpeStatsInfo
        MAX-ACCESS   read-only
        STATUS       current
        DESCRIPTION  
            "RMON 15min TX Queue0 Discard Status. 'invalid' means the
            corresponding monitoring value is not reliable because of the
            alarm or other reasons. 'maintenance' means that some maintenance
            functions are executed on the current interval."
        ::= { rmon15minPort2Entry 68 }

    rmon15minHCTxQueue1Discard2 OBJECT-TYPE
        SYNTAX       Counter64
        MAX-ACCESS   read-only
        STATUS       current
        DESCRIPTION  "RMON 15min TX Queue1 Discard"
        ::= { rmon15minPort2Entry 69 }

    rmon15minHCTxQueue1Discard2Status OBJECT-TYPE
        SYNTAX       IpeStatsInfo
        MAX-ACCESS   read-only
        STATUS       current
        DESCRIPTION  
            "RMON 15min TX Queue1 Discard Status. 'invalid' means the
            corresponding monitoring value is not reliable because of the
            alarm or other reasons. 'maintenance' means that some maintenance
            functions are executed on the current interval."
        ::= { rmon15minPort2Entry 70 }

    rmon15minHCTxQueue2Discard2 OBJECT-TYPE
        SYNTAX       Counter64
        MAX-ACCESS   read-only
        STATUS       current
        DESCRIPTION  "RMON 15min TX Queue2 Discard"
        ::= { rmon15minPort2Entry 71 }

    rmon15minHCTxQueue2Discard2Status OBJECT-TYPE
        SYNTAX       IpeStatsInfo
        MAX-ACCESS   read-only
        STATUS       current
        DESCRIPTION  
            "RMON 15min TX Queue2 Discard Status. 'invalid' means the
            corresponding monitoring value is not reliable because of the
            alarm or other reasons. 'maintenance' means that some maintenance
            functions are executed on the current interval."
        ::= { rmon15minPort2Entry 72 }

    rmon15minHCTxQueue3Discard2 OBJECT-TYPE
        SYNTAX       Counter64
        MAX-ACCESS   read-only
        STATUS       current
        DESCRIPTION  "RMON 15min TX Queue3 Discard"
        ::= { rmon15minPort2Entry 73 }

    rmon15minHCTxQueue3Discard2Status OBJECT-TYPE
        SYNTAX       IpeStatsInfo
        MAX-ACCESS   read-only
        STATUS       current
        DESCRIPTION  
            "RMON 15min TX Queue3 Discard Status. 'invalid' means the
            corresponding monitoring value is not reliable because of the
            alarm or other reasons. 'maintenance' means that some maintenance
            functions are executed on the current interval."
        ::= { rmon15minPort2Entry 74 }

    rmon15minHCTxQueue4Discard2 OBJECT-TYPE
        SYNTAX       Counter64
        MAX-ACCESS   read-only
        STATUS       current
        DESCRIPTION  
            "RMON 15min TX Queue4 Discard. If the equipment is running on 4
            class QoS mode. The value of this object is always 0."
        ::= { rmon15minPort2Entry 75 }

    rmon15minHCTxQueue4Discard2Status OBJECT-TYPE
        SYNTAX       IpeStatsInfo
        MAX-ACCESS   read-only
        STATUS       current
        DESCRIPTION  
            "RMON 15min TX Queue4 Discard Status. 'invalid' means the
            corresponding monitoring value is not reliable because of the
            alarm or other reasons. 'maintenance' means that some maintenance
            functions are executed on the current interval."
        ::= { rmon15minPort2Entry 76 }

    rmon15minHCTxQueue5Discard2 OBJECT-TYPE
        SYNTAX       Counter64
        MAX-ACCESS   read-only
        STATUS       current
        DESCRIPTION  
            "RMON 15min TX Queue5 Discard. If the equipment is running on 4
            class QoS mode. The value of this object is always 0."
        ::= { rmon15minPort2Entry 77 }

    rmon15minHCTxQueue5Discard2Status OBJECT-TYPE
        SYNTAX       IpeStatsInfo
        MAX-ACCESS   read-only
        STATUS       current
        DESCRIPTION  
            "RMON 15min TX Queue5 Discard Status. 'invalid' means the
            corresponding monitoring value is not reliable because of the
            alarm or other reasons. 'maintenance' means that some maintenance
            functions are executed on the current interval."
        ::= { rmon15minPort2Entry 78 }

    rmon15minHCTxQueue6Discard2 OBJECT-TYPE
        SYNTAX       Counter64
        MAX-ACCESS   read-only
        STATUS       current
        DESCRIPTION  
            "RMON 15min TX Queue6 Discard. If the equipment is running on 4
            class QoS mode. The value of this object is always 0."
        ::= { rmon15minPort2Entry 79 }

    rmon15minHCTxQueue6Discard2Status OBJECT-TYPE
        SYNTAX       IpeStatsInfo
        MAX-ACCESS   read-only
        STATUS       current
        DESCRIPTION  
            "RMON 15min TX Queue6 Discard Status. 'invalid' means the
            corresponding monitoring value is not reliable because of the
            alarm or other reasons. 'maintenance' means that some maintenance
            functions are executed on the current interval."
        ::= { rmon15minPort2Entry 80 }

    rmon15minHCTxQueue7Discard2 OBJECT-TYPE
        SYNTAX       Counter64
        MAX-ACCESS   read-only
        STATUS       current
        DESCRIPTION  
            "RMON 15min TX Queue7 Discard. If the equipment is running on 4
            class QoS mode. The value of this object is always 0."
        ::= { rmon15minPort2Entry 81 }

    rmon15minHCTxQueue7Discard2Status OBJECT-TYPE
        SYNTAX       IpeStatsInfo
        MAX-ACCESS   read-only
        STATUS       current
        DESCRIPTION  
            "RMON 15min TX Queue7 Discard Status. 'invalid' means the
            corresponding monitoring value is not reliable because of the
            alarm or other reasons. 'maintenance' means that some maintenance
            functions are executed on the current interval."
        ::= { rmon15minPort2Entry 82 }

    rmon15minTxEthStatsOversizePkts2 OBJECT-TYPE
        SYNTAX       Counter32
        MAX-ACCESS   read-only
        STATUS       current
        DESCRIPTION  "RMON 15min TX Oversize Pkts."
        ::= { rmon15minPort2Entry 83 }

    rmon15minTxEthStatsOversizePkts2Status OBJECT-TYPE
        SYNTAX       IpeStatsInfo
        MAX-ACCESS   read-only
        STATUS       current
        DESCRIPTION  
            "RMON 15min TX Oversize Pkts Status. 'invalid' means the
            corresponding monitoring value is not reliable because of the
            alarm or other reasons. 'maintenance' means that some maintenance
            functions are executed on the current interval."
        ::= { rmon15minPort2Entry 84 }

    rmon15minHCTxFilterDiscard2 OBJECT-TYPE
        SYNTAX       Counter64
        MAX-ACCESS   read-only
        STATUS       current
        DESCRIPTION  "RMON 15min TX Filter Discard"
        ::= { rmon15minPort2Entry 85 }

    rmon15minHCTxFilterDiscard2Status OBJECT-TYPE
        SYNTAX       IpeStatsInfo
        MAX-ACCESS   read-only
        STATUS       current
        DESCRIPTION  
            "RMON 15min TX Filter Discard Status. 'invalid' means the
            corresponding monitoring value is not reliable because of the
            alarm or other reasons. 'maintenance' means that some maintenance
            functions are executed on the current interval."
        ::= { rmon15minPort2Entry 86 }

    rmon15minSfpDataTable OBJECT-TYPE
        SYNTAX       SEQUENCE OF Rmon15minSfpDataEntry
        MAX-ACCESS   not-accessible
        STATUS       current
        DESCRIPTION  "15minutes ETH Port Sfp Tx/Rx Power Monitoring Table"
        ::= { rmon15minPortGroup 3 }

    rmon15minSfpDataEntry OBJECT-TYPE
        SYNTAX       Rmon15minSfpDataEntry
        MAX-ACCESS   not-accessible
        STATUS       current
        DESCRIPTION  ""
        INDEX        { rmon15minSfpDataIfIndex }
        ::= { rmon15minSfpDataTable 1 }

    Rmon15minSfpDataEntry ::= SEQUENCE {
        rmon15minSfpDataIfIndex            InterfaceIndex,
        rmon15minSfpDataNEAddress          IpAddress,
        rmon15minSfpTxPowerDataStatusInfo  IpeStatsInfo,
        rmon15minSfpTxPowerData            DisplayString,
        rmon15minSfpRxPowerDataStatusInfo  IpeStatsInfo,
        rmon15minSfpRxPowerData            DisplayString
    }

    rmon15minSfpDataIfIndex OBJECT-TYPE
        SYNTAX       InterfaceIndex
        MAX-ACCESS   not-accessible
        STATUS       current
        DESCRIPTION  "Index of this table."
        ::= { rmon15minSfpDataEntry 1 }

    rmon15minSfpDataNEAddress OBJECT-TYPE
        SYNTAX       IpAddress
        MAX-ACCESS   not-accessible
        STATUS       current
        DESCRIPTION  "reserved"
        ::= { rmon15minSfpDataEntry 2 }

    rmon15minSfpTxPowerDataStatusInfo OBJECT-TYPE
        SYNTAX       IpeStatsInfo
        MAX-ACCESS   read-only
        STATUS       current
        DESCRIPTION  "15minutes ETH Port Sfp Tx Power."
        ::= { rmon15minSfpDataEntry 3 }

    rmon15minSfpTxPowerData OBJECT-TYPE
        SYNTAX       DisplayString
        MAX-ACCESS   read-only
        STATUS       current
        DESCRIPTION  "15minutes ETH Port Sfp Tx Power Status."
        ::= { rmon15minSfpDataEntry 4 }

    rmon15minSfpRxPowerDataStatusInfo OBJECT-TYPE
        SYNTAX       IpeStatsInfo
        MAX-ACCESS   read-only
        STATUS       current
        DESCRIPTION  "15minutes ETH Port Sfp Rx Power."
        ::= { rmon15minSfpDataEntry 5 }

    rmon15minSfpRxPowerData OBJECT-TYPE
        SYNTAX       DisplayString
        MAX-ACCESS   read-only
        STATUS       current
        DESCRIPTION  "15minutes ETH Port Sfp Rx Power Status."
        ::= { rmon15minSfpDataEntry 6 }

    rmon1dayportGroup OBJECT IDENTIFIER
        ::= { rmonEthGroup 2 }

    rmon1dayPort2Table OBJECT-TYPE
        SYNTAX       SEQUENCE OF Rmon1dayPort2Entry
        MAX-ACCESS   not-accessible
        STATUS       current
        DESCRIPTION  "RMON 1day Port Monitoring Table."
        ::= { rmon1dayportGroup 2 }

    rmon1dayPort2Entry OBJECT-TYPE
        SYNTAX       Rmon1dayPort2Entry
        MAX-ACCESS   not-accessible
        STATUS       current
        DESCRIPTION  ""
        INDEX        { rmon1dayPort2IfIndex }
        ::= { rmon1dayPort2Table 1 }

    Rmon1dayPort2Entry ::= SEQUENCE {
        rmon1dayPort2IfIndex                             InterfaceIndex,
        rmon1dayPort2NEAddress                           IpAddress,
        rmon1dayHCRxEthStatsOctets2                      Counter64,
        rmon1dayHCRxEthStatsOctets2Status                IpeStatsInfo,
        rmon1dayHCTxEthStatsOctets2                      Counter64,
        rmon1dayHCTxEthStatsOctets2Status                IpeStatsInfo,
        rmon1dayHCRxEthStatsPkts2                        Counter64,
        rmon1dayHCRxEthStatsPkts2Status                  IpeStatsInfo,
        rmon1dayHCTxEthStatsPkts2                        Counter64,
        rmon1dayHCTxEthStatsPkts2Status                  IpeStatsInfo,
        rmon1dayRxEthStatsDropEvents2                    Counter32,
        rmon1dayRxEthStatsDropEvents2Status              IpeStatsInfo,
        rmon1dayRxEthStatsUndersizePkts2                 Counter32,
        rmon1dayRxEthStatsUndersizePkts2Status           IpeStatsInfo,
        rmon1dayRxEthStatsFragments2                     Counter32,
        rmon1dayRxEthStatsFragments2Status               IpeStatsInfo,
        rmon1dayHCRxEthStatsPkts64Octets2                Counter64,
        rmon1dayHCRxEthStatsPkts64Octets2Status          IpeStatsInfo,
        rmon1dayHCTxEthStatsPkts64Octets2                Counter64,
        rmon1dayHCTxEthStatsPkts64Octets2Status          IpeStatsInfo,
        rmon1dayHCRxEthStatsPkts65to127Octets2           Counter64,
        rmon1dayHCRxEthStatsPkts65to127Octets2Status     IpeStatsInfo,
        rmon1dayHCTxEthStatsPkts65to127Octets2           Counter64,
        rmon1dayHCTxEthStatsPkts65to127Octets2Status     IpeStatsInfo,
        rmon1dayHCRxEthStatsPkts128to255Octets2          Counter64,
        rmon1dayHCRxEthStatsPkts128to255Octets2Status    IpeStatsInfo,
        rmon1dayHCTxEthStatsPkts128to255Octets2          Counter64,
        rmon1dayHCTxEthStatsPkts128to255Octets2Status    IpeStatsInfo,
        rmon1dayHCRxEthStatsPkts256to511Octets2          Counter64,
        rmon1dayHCRxEthStatsPkts256to511Octets2Status    IpeStatsInfo,
        rmon1dayHCTxEthStatsPkts256to511Octets2          Counter64,
        rmon1dayHCTxEthStatsPkts256to511Octets2Status    IpeStatsInfo,
        rmon1dayHCRxEthStatsPkts512to1023Octets2         Counter64,
        rmon1dayHCRxEthStatsPkts512to1023Octets2Status   IpeStatsInfo,
        rmon1dayHCTxEthStatsPkts512to1023Octets2         Counter64,
        rmon1dayHCTxEthStatsPkts512to1023Octets2Status   IpeStatsInfo,
        rmon1dayHCRxEthStatsPkts1024to1518Octets2        Counter64,
        rmon1dayHCRxEthStatsPkts1024to1518Octets2Status  IpeStatsInfo,
        rmon1dayHCTxEthStatsPkts1024to1518Octets2        Counter64,
        rmon1dayHCTxEthStatsPkts1024to1518Octets2Status  IpeStatsInfo,
        rmon1dayRxEthStatsCRCAlignErrors2                Counter32,
        rmon1dayRxEthStatsCRCAlignErrors2Status          IpeStatsInfo,
        rmon1dayRxEthStatsOversizePkts2                  Counter32,
        rmon1dayRxEthStatsOversizePkts2Status            IpeStatsInfo,
        rmon1dayRxEthStatsJabbers2                       Counter32,
        rmon1dayRxEthStatsJabbers2Status                 IpeStatsInfo,
        rmon1dayRxEthStatsMulticastPkts2                 Counter32,
        rmon1dayRxEthStatsMulticastPkts2Status           IpeStatsInfo,
        rmon1dayTxEthStatsMulticastPkts2                 Counter32,
        rmon1dayTxEthStatsMulticastPkts2Status           IpeStatsInfo,
        rmon1dayRxEthStatsBroadcastPkts2                 Counter32,
        rmon1dayRxEthStatsBroadcastPkts2Status           IpeStatsInfo,
        rmon1dayTxEthStatsBroadcastPkts2                 Counter32,
        rmon1dayTxEthStatsBroadcastPkts2Status           IpeStatsInfo,
        rmon1dayTxEthStatsCollisions2                    Counter32,
        rmon1dayTxEthStatsCollisions2Status              IpeStatsInfo,
        rmon1dayHCRxUnknownTPID2                         Counter64,
        rmon1dayHCRxUnknownTPID2Status                   IpeStatsInfo,
        rmon1dayHCRxUnknownVID2                          Counter64,
        rmon1dayHCRxUnknownVID2Status                    IpeStatsInfo,
        rmon1dayHCRxMAClimit2                            Counter64,
        rmon1dayHCRxMAClimit2Status                      IpeStatsInfo,
        rmon1dayHCRxFilterDiscard2                       Counter64,
        rmon1dayHCRxFilterDiscard2Status                 IpeStatsInfo,
        rmon1dayHCRxQoSDiscard2                          Counter64,
        rmon1dayHCRxQoSDiscard2Status                    IpeStatsInfo,
        rmon1dayHCTxQueue0Discard2                       Counter64,
        rmon1dayHCTxQueue0Discard2Status                 IpeStatsInfo,
        rmon1dayHCTxQueue1Discard2                       Counter64,
        rmon1dayHCTxQueue1Discard2Status                 IpeStatsInfo,
        rmon1dayHCTxQueue2Discard2                       Counter64,
        rmon1dayHCTxQueue2Discard2Status                 IpeStatsInfo,
        rmon1dayHCTxQueue3Discard2                       Counter64,
        rmon1dayHCTxQueue3Discard2Status                 IpeStatsInfo,
        rmon1dayHCTxQueue4Discard2                       Counter64,
        rmon1dayHCTxQueue4Discard2Status                 IpeStatsInfo,
        rmon1dayHCTxQueue5Discard2                       Counter64,
        rmon1dayHCTxQueue5Discard2Status                 IpeStatsInfo,
        rmon1dayHCTxQueue6Discard2                       Counter64,
        rmon1dayHCTxQueue6Discard2Status                 IpeStatsInfo,
        rmon1dayHCTxQueue7Discard2                       Counter64,
        rmon1dayHCTxQueue7Discard2Status                 IpeStatsInfo,
        rmon1dayTxEthStatsOversizePkts2                  Counter32,
        rmon1dayTxEthStatsOversizePkts2Status            IpeStatsInfo,
        rmon1dayHCTxFilterDiscard2                       Counter64,
        rmon1dayHCTxFilterDiscard2Status                 IpeStatsInfo
    }

    rmon1dayPort2IfIndex OBJECT-TYPE
        SYNTAX       InterfaceIndex
        MAX-ACCESS   not-accessible
        STATUS       current
        DESCRIPTION  "Index of this table."
        ::= { rmon1dayPort2Entry 1 }

    rmon1dayPort2NEAddress OBJECT-TYPE
        SYNTAX       IpAddress
        MAX-ACCESS   not-accessible
        STATUS       current
        DESCRIPTION  "reserved."
        ::= { rmon1dayPort2Entry 2 }

    rmon1dayHCRxEthStatsOctets2 OBJECT-TYPE
        SYNTAX       Counter64
        MAX-ACCESS   read-only
        STATUS       current
        DESCRIPTION  "RMON 1day RX Octs"
        ::= { rmon1dayPort2Entry 3 }

    rmon1dayHCRxEthStatsOctets2Status OBJECT-TYPE
        SYNTAX       IpeStatsInfo
        MAX-ACCESS   read-only
        STATUS       current
        DESCRIPTION  
            "RMON 1day RX Octs Status. 'invalid' means the corresponding
            monitoring value is not reliable because of the alarm or other
            reasons. 'maintenance' means that some maintenance functions are
            executed on the current interval."
        ::= { rmon1dayPort2Entry 4 }

    rmon1dayHCTxEthStatsOctets2 OBJECT-TYPE
        SYNTAX       Counter64
        MAX-ACCESS   read-only
        STATUS       current
        DESCRIPTION  "RMON 1day TX Octs"
        ::= { rmon1dayPort2Entry 5 }

    rmon1dayHCTxEthStatsOctets2Status OBJECT-TYPE
        SYNTAX       IpeStatsInfo
        MAX-ACCESS   read-only
        STATUS       current
        DESCRIPTION  
            "RMON 1day TX Octs Status. 'invalid' means the corresponding
            monitoring value is not reliable because of the alarm or other
            reasons. 'maintenance' means that some maintenance functions are
            executed on the current interval."
        ::= { rmon1dayPort2Entry 6 }

    rmon1dayHCRxEthStatsPkts2 OBJECT-TYPE
        SYNTAX       Counter64
        MAX-ACCESS   read-only
        STATUS       current
        DESCRIPTION  "RMON 1day RX Pkts"
        ::= { rmon1dayPort2Entry 7 }

    rmon1dayHCRxEthStatsPkts2Status OBJECT-TYPE
        SYNTAX       IpeStatsInfo
        MAX-ACCESS   read-only
        STATUS       current
        DESCRIPTION  
            "RMON 1day RX Pkts Status. 'invalid' means the corresponding
            monitoring value is not reliable because of the alarm or other
            reasons. 'maintenance' means that some maintenance functions are
            executed on the current interval."
        ::= { rmon1dayPort2Entry 8 }

    rmon1dayHCTxEthStatsPkts2 OBJECT-TYPE
        SYNTAX       Counter64
        MAX-ACCESS   read-only
        STATUS       current
        DESCRIPTION  "RMON 1day TX Pkts"
        ::= { rmon1dayPort2Entry 9 }

    rmon1dayHCTxEthStatsPkts2Status OBJECT-TYPE
        SYNTAX       IpeStatsInfo
        MAX-ACCESS   read-only
        STATUS       current
        DESCRIPTION  
            "RMON 1day TX Pkts Status. 'invalid' means the corresponding
            monitoring value is not reliable because of the alarm or other
            reasons. 'maintenance' means that some maintenance functions are
            executed on the current interval."
        ::= { rmon1dayPort2Entry 10 }

    rmon1dayRxEthStatsDropEvents2 OBJECT-TYPE
        SYNTAX       Counter32
        MAX-ACCESS   read-only
        STATUS       current
        DESCRIPTION  "RMON 1day RX Drop Events"
        ::= { rmon1dayPort2Entry 11 }

    rmon1dayRxEthStatsDropEvents2Status OBJECT-TYPE
        SYNTAX       IpeStatsInfo
        MAX-ACCESS   read-only
        STATUS       current
        DESCRIPTION  
            "RMON 1day RX Drop Events Status. 'invalid' means the
            corresponding monitoring value is not reliable because of the
            alarm or other reasons. 'maintenance' means that some maintenance
            functions are executed on the current interval."
        ::= { rmon1dayPort2Entry 12 }

    rmon1dayRxEthStatsUndersizePkts2 OBJECT-TYPE
        SYNTAX       Counter32
        MAX-ACCESS   read-only
        STATUS       current
        DESCRIPTION  "RMON 1day RX Undersize Pkts"
        ::= { rmon1dayPort2Entry 13 }

    rmon1dayRxEthStatsUndersizePkts2Status OBJECT-TYPE
        SYNTAX       IpeStatsInfo
        MAX-ACCESS   read-only
        STATUS       current
        DESCRIPTION  
            "RMON 1day RX Undersize Pkts Status. 'invalid' means the
            corresponding monitoring value is not reliable because of the
            alarm or other reasons. 'maintenance' means that some maintenance
            functions are executed on the current interval."
        ::= { rmon1dayPort2Entry 14 }

    rmon1dayRxEthStatsFragments2 OBJECT-TYPE
        SYNTAX       Counter32
        MAX-ACCESS   read-only
        STATUS       current
        DESCRIPTION  "RMON 1day RX Fragments"
        ::= { rmon1dayPort2Entry 15 }

    rmon1dayRxEthStatsFragments2Status OBJECT-TYPE
        SYNTAX       IpeStatsInfo
        MAX-ACCESS   read-only
        STATUS       current
        DESCRIPTION  
            "RMON 1day RX Fragments Status. 'invalid' means the corresponding
            monitoring value is not reliable because of the alarm or other
            reasons. 'maintenance' means that some maintenance functions are
            executed on the current interval."
        ::= { rmon1dayPort2Entry 16 }

    rmon1dayHCRxEthStatsPkts64Octets2 OBJECT-TYPE
        SYNTAX       Counter64
        MAX-ACCESS   read-only
        STATUS       current
        DESCRIPTION  "RMON 1day RX 64 Octs"
        ::= { rmon1dayPort2Entry 17 }

    rmon1dayHCRxEthStatsPkts64Octets2Status OBJECT-TYPE
        SYNTAX       IpeStatsInfo
        MAX-ACCESS   read-only
        STATUS       current
        DESCRIPTION  
            "RMON 1day RX 64 Octs Status. 'invalid' means the corresponding
            monitoring value is not reliable because of the alarm or other
            reasons. 'maintenance' means that some maintenance functions are
            executed on the current interval."
        ::= { rmon1dayPort2Entry 18 }

    rmon1dayHCTxEthStatsPkts64Octets2 OBJECT-TYPE
        SYNTAX       Counter64
        MAX-ACCESS   read-only
        STATUS       current
        DESCRIPTION  "RMON 1day TX 64 Octs"
        ::= { rmon1dayPort2Entry 19 }

    rmon1dayHCTxEthStatsPkts64Octets2Status OBJECT-TYPE
        SYNTAX       IpeStatsInfo
        MAX-ACCESS   read-only
        STATUS       current
        DESCRIPTION  
            "RMON 1day TX 64 Octs Status. 'invalid' means the corresponding
            monitoring value is not reliable because of the alarm or other
            reasons. 'maintenance' means that some maintenance functions are
            executed on the current interval."
        ::= { rmon1dayPort2Entry 20 }

    rmon1dayHCRxEthStatsPkts65to127Octets2 OBJECT-TYPE
        SYNTAX       Counter64
        MAX-ACCESS   read-only
        STATUS       current
        DESCRIPTION  "RMON 1day RX 65 to 127 Octs"
        ::= { rmon1dayPort2Entry 21 }

    rmon1dayHCRxEthStatsPkts65to127Octets2Status OBJECT-TYPE
        SYNTAX       IpeStatsInfo
        MAX-ACCESS   read-only
        STATUS       current
        DESCRIPTION  
            "RMON 1day RX 65 to 127 Octs Status. 'invalid' means the
            corresponding monitoring value is not reliable because of the
            alarm or other reasons. 'maintenance' means that some maintenance
            functions are executed on the current interval."
        ::= { rmon1dayPort2Entry 22 }

    rmon1dayHCTxEthStatsPkts65to127Octets2 OBJECT-TYPE
        SYNTAX       Counter64
        MAX-ACCESS   read-only
        STATUS       current
        DESCRIPTION  "RMON 1day TX 65 to 127 Octs"
        ::= { rmon1dayPort2Entry 23 }

    rmon1dayHCTxEthStatsPkts65to127Octets2Status OBJECT-TYPE
        SYNTAX       IpeStatsInfo
        MAX-ACCESS   read-only
        STATUS       current
        DESCRIPTION  
            "RMON 1day TX 65 to 127 Octs Status. 'invalid' means the
            corresponding monitoring value is not reliable because of the
            alarm or other reasons. 'maintenance' means that some maintenance
            functions are executed on the current interval."
        ::= { rmon1dayPort2Entry 24 }

    rmon1dayHCRxEthStatsPkts128to255Octets2 OBJECT-TYPE
        SYNTAX       Counter64
        MAX-ACCESS   read-only
        STATUS       current
        DESCRIPTION  "RMON 1day RX 128 to 255 Octs."
        ::= { rmon1dayPort2Entry 25 }

    rmon1dayHCRxEthStatsPkts128to255Octets2Status OBJECT-TYPE
        SYNTAX       IpeStatsInfo
        MAX-ACCESS   read-only
        STATUS       current
        DESCRIPTION  
            "RMON 1day RX 128 to 255 Octs Status. 'invalid' means the
            corresponding monitoring value is not reliable because of the
            alarm or other reasons. 'maintenance' means that some maintenance
            functions are executed on the current interval."
        ::= { rmon1dayPort2Entry 26 }

    rmon1dayHCTxEthStatsPkts128to255Octets2 OBJECT-TYPE
        SYNTAX       Counter64
        MAX-ACCESS   read-only
        STATUS       current
        DESCRIPTION  "RMON 1day TX 128 to 255 Octs"
        ::= { rmon1dayPort2Entry 27 }

    rmon1dayHCTxEthStatsPkts128to255Octets2Status OBJECT-TYPE
        SYNTAX       IpeStatsInfo
        MAX-ACCESS   read-only
        STATUS       current
        DESCRIPTION  
            "RMON 1day TX 128 to 255 Octs Status. 'invalid' means the
            corresponding monitoring value is not reliable because of the
            alarm or other reasons. 'maintenance' means that some maintenance
            functions are executed on the current interval."
        ::= { rmon1dayPort2Entry 28 }

    rmon1dayHCRxEthStatsPkts256to511Octets2 OBJECT-TYPE
        SYNTAX       Counter64
        MAX-ACCESS   read-only
        STATUS       current
        DESCRIPTION  "RMON 1day RX 256 to 511 Octs."
        ::= { rmon1dayPort2Entry 29 }

    rmon1dayHCRxEthStatsPkts256to511Octets2Status OBJECT-TYPE
        SYNTAX       IpeStatsInfo
        MAX-ACCESS   read-only
        STATUS       current
        DESCRIPTION  
            "RMON 1day RX 256 to 511 Octs Status. 'invalid' means the
            corresponding monitoring value is not reliable because of the
            alarm or other reasons. 'maintenance' means that some maintenance
            functions are executed on the current interval."
        ::= { rmon1dayPort2Entry 30 }

    rmon1dayHCTxEthStatsPkts256to511Octets2 OBJECT-TYPE
        SYNTAX       Counter64
        MAX-ACCESS   read-only
        STATUS       current
        DESCRIPTION  "RMON 1day TX 256 to 511 Octs."
        ::= { rmon1dayPort2Entry 31 }

    rmon1dayHCTxEthStatsPkts256to511Octets2Status OBJECT-TYPE
        SYNTAX       IpeStatsInfo
        MAX-ACCESS   read-only
        STATUS       current
        DESCRIPTION  
            "RMON 1day TX 256 to 511 Octs Status. 'invalid' means the
            corresponding monitoring value is not reliable because of the
            alarm or other reasons. 'maintenance' means that some maintenance
            functions are executed on the current interval."
        ::= { rmon1dayPort2Entry 32 }

    rmon1dayHCRxEthStatsPkts512to1023Octets2 OBJECT-TYPE
        SYNTAX       Counter64
        MAX-ACCESS   read-only
        STATUS       current
        DESCRIPTION  "RMON 1day RX 512 to 1023 Octs"
        ::= { rmon1dayPort2Entry 33 }

    rmon1dayHCRxEthStatsPkts512to1023Octets2Status OBJECT-TYPE
        SYNTAX       IpeStatsInfo
        MAX-ACCESS   read-only
        STATUS       current
        DESCRIPTION  
            "RMON 1day RX 512 to 1023 Octs Status. 'invalid' means the
            corresponding monitoring value is not reliable because of the
            alarm or other reasons. 'maintenance' means that some maintenance
            functions are executed on the current interval."
        ::= { rmon1dayPort2Entry 34 }

    rmon1dayHCTxEthStatsPkts512to1023Octets2 OBJECT-TYPE
        SYNTAX       Counter64
        MAX-ACCESS   read-only
        STATUS       current
        DESCRIPTION  "RMON 1day TX 512 to 1023 Octs"
        ::= { rmon1dayPort2Entry 35 }

    rmon1dayHCTxEthStatsPkts512to1023Octets2Status OBJECT-TYPE
        SYNTAX       IpeStatsInfo
        MAX-ACCESS   read-only
        STATUS       current
        DESCRIPTION  
            "RMON 1day TX 512 to 1023 Octs Status. 'invalid' means the
            corresponding monitoring value is not reliable because of the
            alarm or other reasons. 'maintenance' means that some maintenance
            functions are executed on the current interval."
        ::= { rmon1dayPort2Entry 36 }

    rmon1dayHCRxEthStatsPkts1024to1518Octets2 OBJECT-TYPE
        SYNTAX       Counter64
        MAX-ACCESS   read-only
        STATUS       current
        DESCRIPTION  "RMON 1day RX 1024 to 1518 Octs."
        ::= { rmon1dayPort2Entry 37 }

    rmon1dayHCRxEthStatsPkts1024to1518Octets2Status OBJECT-TYPE
        SYNTAX       IpeStatsInfo
        MAX-ACCESS   read-only
        STATUS       current
        DESCRIPTION  
            "RMON 1day RX 1024 to 1518 Octs Status. 'invalid' means the
            corresponding monitoring value is not reliable because of the
            alarm or other reasons. 'maintenance' means that some maintenance
            functions are executed on the current interval."
        ::= { rmon1dayPort2Entry 38 }

    rmon1dayHCTxEthStatsPkts1024to1518Octets2 OBJECT-TYPE
        SYNTAX       Counter64
        MAX-ACCESS   read-only
        STATUS       current
        DESCRIPTION  "RMON 1day TX 1024 to 1518 Octs."
        ::= { rmon1dayPort2Entry 39 }

    rmon1dayHCTxEthStatsPkts1024to1518Octets2Status OBJECT-TYPE
        SYNTAX       IpeStatsInfo
        MAX-ACCESS   read-only
        STATUS       current
        DESCRIPTION  
            "RMON 1day TX 1024 to 1518 Octs Status. 'invalid' means the
            corresponding monitoring value is not reliable because of the
            alarm or other reasons. 'maintenance' means that some maintenance
            functions are executed on the current interval."
        ::= { rmon1dayPort2Entry 40 }

    rmon1dayRxEthStatsCRCAlignErrors2 OBJECT-TYPE
        SYNTAX       Counter32
        MAX-ACCESS   read-only
        STATUS       current
        DESCRIPTION  "RMON 1day RX CRC Alignment Errors"
        ::= { rmon1dayPort2Entry 41 }

    rmon1dayRxEthStatsCRCAlignErrors2Status OBJECT-TYPE
        SYNTAX       IpeStatsInfo
        MAX-ACCESS   read-only
        STATUS       current
        DESCRIPTION  
            "RMON 1day RX CRC Alignment Errors Status. 'invalid' means the
            corresponding monitoring value is not reliable because of the
            alarm or other reasons. 'maintenance' means that some maintenance
            functions are executed on the current interval."
        ::= { rmon1dayPort2Entry 42 }

    rmon1dayRxEthStatsOversizePkts2 OBJECT-TYPE
        SYNTAX       Counter32
        MAX-ACCESS   read-only
        STATUS       current
        DESCRIPTION  "RMON 1day RX Oversize Pkts"
        ::= { rmon1dayPort2Entry 43 }

    rmon1dayRxEthStatsOversizePkts2Status OBJECT-TYPE
        SYNTAX       IpeStatsInfo
        MAX-ACCESS   read-only
        STATUS       current
        DESCRIPTION  
            "RMON 1day RX Oversize Pkts Status. 'invalid' means the
            corresponding monitoring value is not reliable because of the
            alarm or other reasons. 'maintenance' means that some maintenance
            functions are executed on the current interval."
        ::= { rmon1dayPort2Entry 44 }

    rmon1dayRxEthStatsJabbers2 OBJECT-TYPE
        SYNTAX       Counter32
        MAX-ACCESS   read-only
        STATUS       current
        DESCRIPTION  "RMON 1day RX Jabbers"
        ::= { rmon1dayPort2Entry 45 }

    rmon1dayRxEthStatsJabbers2Status OBJECT-TYPE
        SYNTAX       IpeStatsInfo
        MAX-ACCESS   read-only
        STATUS       current
        DESCRIPTION  
            "RMON 1day RX Jabbers Status. 'invalid' means the corresponding
            monitoring value is not reliable because of the alarm or other
            reasons. 'maintenance' means that some maintenance functions are
            executed on the current interval."
        ::= { rmon1dayPort2Entry 46 }

    rmon1dayRxEthStatsMulticastPkts2 OBJECT-TYPE
        SYNTAX       Counter32
        MAX-ACCESS   read-only
        STATUS       current
        DESCRIPTION  "RMON 1day RX Multicast Pkts"
        ::= { rmon1dayPort2Entry 47 }

    rmon1dayRxEthStatsMulticastPkts2Status OBJECT-TYPE
        SYNTAX       IpeStatsInfo
        MAX-ACCESS   read-only
        STATUS       current
        DESCRIPTION  
            "RMON 1day RX Multicast Pkts Status. 'invalid' means the
            corresponding monitoring value is not reliable because of the
            alarm or other reasons. 'maintenance' means that some maintenance
            functions are executed on the current interval."
        ::= { rmon1dayPort2Entry 48 }

    rmon1dayTxEthStatsMulticastPkts2 OBJECT-TYPE
        SYNTAX       Counter32
        MAX-ACCESS   read-only
        STATUS       current
        DESCRIPTION  "RMON 1day TX Multicast Pkts."
        ::= { rmon1dayPort2Entry 49 }

    rmon1dayTxEthStatsMulticastPkts2Status OBJECT-TYPE
        SYNTAX       IpeStatsInfo
        MAX-ACCESS   read-only
        STATUS       current
        DESCRIPTION  
            "RMON 1day TX Multicast Pkts Status. 'invalid' means the
            corresponding monitoring value is not reliable because of the
            alarm or other reasons. 'maintenance' means that some maintenance
            functions are executed on the current interval."
        ::= { rmon1dayPort2Entry 50 }

    rmon1dayRxEthStatsBroadcastPkts2 OBJECT-TYPE
        SYNTAX       Counter32
        MAX-ACCESS   read-only
        STATUS       current
        DESCRIPTION  "RMON 1day RX Broadcast Pkts."
        ::= { rmon1dayPort2Entry 51 }

    rmon1dayRxEthStatsBroadcastPkts2Status OBJECT-TYPE
        SYNTAX       IpeStatsInfo
        MAX-ACCESS   read-only
        STATUS       current
        DESCRIPTION  
            "RMON 1day RX Broadcast Pkts Status. 'invalid' means the
            corresponding monitoring value is not reliable because of the
            alarm or other reasons. 'maintenance' means that some maintenance
            functions are executed on the current interval."
        ::= { rmon1dayPort2Entry 52 }

    rmon1dayTxEthStatsBroadcastPkts2 OBJECT-TYPE
        SYNTAX       Counter32
        MAX-ACCESS   read-only
        STATUS       current
        DESCRIPTION  "RMON 1day TX Broadcast Pkts."
        ::= { rmon1dayPort2Entry 53 }

    rmon1dayTxEthStatsBroadcastPkts2Status OBJECT-TYPE
        SYNTAX       IpeStatsInfo
        MAX-ACCESS   read-only
        STATUS       current
        DESCRIPTION  
            "RMON 1day TX Broadcast Pkts Status. 'invalid' means the
            corresponding monitoring value is not reliable because of the
            alarm or other reasons. 'maintenance' means that some maintenance
            functions are executed on the current interval."
        ::= { rmon1dayPort2Entry 54 }

    rmon1dayTxEthStatsCollisions2 OBJECT-TYPE
        SYNTAX       Counter32
        MAX-ACCESS   read-only
        STATUS       current
        DESCRIPTION  "RMON 1day TX Collisions."
        ::= { rmon1dayPort2Entry 55 }

    rmon1dayTxEthStatsCollisions2Status OBJECT-TYPE
        SYNTAX       IpeStatsInfo
        MAX-ACCESS   read-only
        STATUS       current
        DESCRIPTION  
            "RMON 1day TX Collistions Status. 'invalid' means the
            corresponding monitoring value is not reliable because of the
            alarm or other reasons. 'maintenance' means that some maintenance
            functions are executed on the current interval."
        ::= { rmon1dayPort2Entry 56 }

    rmon1dayHCRxUnknownTPID2 OBJECT-TYPE
        SYNTAX       Counter64
        MAX-ACCESS   read-only
        STATUS       current
        DESCRIPTION  "RMON 1day RX Unknown TPID."
        ::= { rmon1dayPort2Entry 57 }

    rmon1dayHCRxUnknownTPID2Status OBJECT-TYPE
        SYNTAX       IpeStatsInfo
        MAX-ACCESS   read-only
        STATUS       current
        DESCRIPTION  
            "RMON 1day RX Unknown TPID Status. 'invalid' means the
            corresponding monitoring value is not reliable because of the
            alarm or other reasons. 'maintenance' means that some maintenance
            functions are executed on the current interval."
        ::= { rmon1dayPort2Entry 58 }

    rmon1dayHCRxUnknownVID2 OBJECT-TYPE
        SYNTAX       Counter64
        MAX-ACCESS   read-only
        STATUS       current
        DESCRIPTION  "RMON 1day RX Unknown VID."
        ::= { rmon1dayPort2Entry 59 }

    rmon1dayHCRxUnknownVID2Status OBJECT-TYPE
        SYNTAX       IpeStatsInfo
        MAX-ACCESS   read-only
        STATUS       current
        DESCRIPTION  
            "RMON 1day RX Unknown VID Status. 'invalid' means the
            corresponding monitoring value is not reliable because of the
            alarm or other reasons. 'maintenance' means that some maintenance
            functions are executed on the current interval."
        ::= { rmon1dayPort2Entry 60 }

    rmon1dayHCRxMAClimit2 OBJECT-TYPE
        SYNTAX       Counter64
        MAX-ACCESS   read-only
        STATUS       current
        DESCRIPTION  "RMON 1day RX MAC Limit."
        ::= { rmon1dayPort2Entry 61 }

    rmon1dayHCRxMAClimit2Status OBJECT-TYPE
        SYNTAX       IpeStatsInfo
        MAX-ACCESS   read-only
        STATUS       current
        DESCRIPTION  
            "RMON 1day RX MAC Limit Status. 'invalid' means the corresponding
            monitoring value is not reliable because of the alarm or other
            reasons. 'maintenance' means that some maintenance functions are
            executed on the current interval."
        ::= { rmon1dayPort2Entry 62 }

    rmon1dayHCRxFilterDiscard2 OBJECT-TYPE
        SYNTAX       Counter64
        MAX-ACCESS   read-only
        STATUS       current
        DESCRIPTION  "RMON 1day RX Filter Discard."
        ::= { rmon1dayPort2Entry 63 }

    rmon1dayHCRxFilterDiscard2Status OBJECT-TYPE
        SYNTAX       IpeStatsInfo
        MAX-ACCESS   read-only
        STATUS       current
        DESCRIPTION  
            "RMON 1day RX Filter Discard Status. 'invalid' means the
            corresponding monitoring value is not reliable because of the
            alarm or other reasons. 'maintenance' means that some maintenance
            functions are executed on the current interval."
        ::= { rmon1dayPort2Entry 64 }

    rmon1dayHCRxQoSDiscard2 OBJECT-TYPE
        SYNTAX       Counter64
        MAX-ACCESS   read-only
        STATUS       current
        DESCRIPTION  "RMON 1day RX QoS Discard."
        ::= { rmon1dayPort2Entry 65 }

    rmon1dayHCRxQoSDiscard2Status OBJECT-TYPE
        SYNTAX       IpeStatsInfo
        MAX-ACCESS   read-only
        STATUS       current
        DESCRIPTION  
            "RMON 1day RX QoS Discard Status. 'invalid' means the
            corresponding monitoring value is not reliable because of the
            alarm or other reasons. 'maintenance' means that some maintenance
            functions are executed on the current interval."
        ::= { rmon1dayPort2Entry 66 }

    rmon1dayHCTxQueue0Discard2 OBJECT-TYPE
        SYNTAX       Counter64
        MAX-ACCESS   read-only
        STATUS       current
        DESCRIPTION  "RMON 1day TX Queue0 Discard."
        ::= { rmon1dayPort2Entry 67 }

    rmon1dayHCTxQueue0Discard2Status OBJECT-TYPE
        SYNTAX       IpeStatsInfo
        MAX-ACCESS   read-only
        STATUS       current
        DESCRIPTION  
            "RMON 1day TX Queue0 Discard Status. 'invalid' means the
            corresponding monitoring value is not reliable because of the
            alarm or other reasons. 'maintenance' means that some maintenance
            functions are executed on the current interval."
        ::= { rmon1dayPort2Entry 68 }

    rmon1dayHCTxQueue1Discard2 OBJECT-TYPE
        SYNTAX       Counter64
        MAX-ACCESS   read-only
        STATUS       current
        DESCRIPTION  "RMON 1day TX Queue1 Discard."
        ::= { rmon1dayPort2Entry 69 }

    rmon1dayHCTxQueue1Discard2Status OBJECT-TYPE
        SYNTAX       IpeStatsInfo
        MAX-ACCESS   read-only
        STATUS       current
        DESCRIPTION  
            "RMON 1day TX Queue1 Discard Status. 'invalid' means the
            corresponding monitoring value is not reliable because of the
            alarm or other reasons. 'maintenance' means that some maintenance
            functions are executed on the current interval."
        ::= { rmon1dayPort2Entry 70 }

    rmon1dayHCTxQueue2Discard2 OBJECT-TYPE
        SYNTAX       Counter64
        MAX-ACCESS   read-only
        STATUS       current
        DESCRIPTION  "RMON 1day TX Queue2 Discard."
        ::= { rmon1dayPort2Entry 71 }

    rmon1dayHCTxQueue2Discard2Status OBJECT-TYPE
        SYNTAX       IpeStatsInfo
        MAX-ACCESS   read-only
        STATUS       current
        DESCRIPTION  
            "RMON 1day TX Queue2 Discard Status. 'invalid' means the
            corresponding monitoring value is not reliable because of the
            alarm or other reasons. 'maintenance' means that some maintenance
            functions are executed on the current interval."
        ::= { rmon1dayPort2Entry 72 }

    rmon1dayHCTxQueue3Discard2 OBJECT-TYPE
        SYNTAX       Counter64
        MAX-ACCESS   read-only
        STATUS       current
        DESCRIPTION  "RMON 1day TX Queue3 Discard."
        ::= { rmon1dayPort2Entry 73 }

    rmon1dayHCTxQueue3Discard2Status OBJECT-TYPE
        SYNTAX       IpeStatsInfo
        MAX-ACCESS   read-only
        STATUS       current
        DESCRIPTION  
            "RMON 1day TX Queue3 Discard Status. 'invalid' means the
            corresponding monitoring value is not reliable because of the
            alarm or other reasons. 'maintenance' means that some maintenance
            functions are executed on the current interval."
        ::= { rmon1dayPort2Entry 74 }

    rmon1dayHCTxQueue4Discard2 OBJECT-TYPE
        SYNTAX       Counter64
        MAX-ACCESS   read-only
        STATUS       current
        DESCRIPTION  
            "RMON 1day TX Queue4 Discard. If the equipment is running on 4
            class QoS mode. The value of this object is always 0."
        ::= { rmon1dayPort2Entry 75 }

    rmon1dayHCTxQueue4Discard2Status OBJECT-TYPE
        SYNTAX       IpeStatsInfo
        MAX-ACCESS   read-only
        STATUS       current
        DESCRIPTION  
            "RMON 1day TX Queue4 Discard Status. 'invalid' means the
            corresponding monitoring value is not reliable because of the
            alarm or other reasons. 'maintenance' means that some maintenance
            functions are executed on the current interval."
        ::= { rmon1dayPort2Entry 76 }

    rmon1dayHCTxQueue5Discard2 OBJECT-TYPE
        SYNTAX       Counter64
        MAX-ACCESS   read-only
        STATUS       current
        DESCRIPTION  
            "RMON 1day TX Queue5 Discard. If the equipment is running on 4
            class QoS mode. The value of this object is always 0."
        ::= { rmon1dayPort2Entry 77 }

    rmon1dayHCTxQueue5Discard2Status OBJECT-TYPE
        SYNTAX       IpeStatsInfo
        MAX-ACCESS   read-only
        STATUS       current
        DESCRIPTION  
            "RMON 1day TX Queue5 Discard Status. 'invalid' means the
            corresponding monitoring value is not reliable because of the
            alarm or other reasons. 'maintenance' means that some maintenance
            functions are executed on the current interval."
        ::= { rmon1dayPort2Entry 78 }

    rmon1dayHCTxQueue6Discard2 OBJECT-TYPE
        SYNTAX       Counter64
        MAX-ACCESS   read-only
        STATUS       current
        DESCRIPTION  
            "RMON 1day TX Queue6 Discard. If the equipment is running on 4
            class QoS mode. The value of this object is always 0."
        ::= { rmon1dayPort2Entry 79 }

    rmon1dayHCTxQueue6Discard2Status OBJECT-TYPE
        SYNTAX       IpeStatsInfo
        MAX-ACCESS   read-only
        STATUS       current
        DESCRIPTION  
            "RMON 1day TX Queue6 Discard Status. 'invalid' means the
            corresponding monitoring value is not reliable because of the
            alarm or other reasons. 'maintenance' means that some maintenance
            functions are executed on the current interval."
        ::= { rmon1dayPort2Entry 80 }

    rmon1dayHCTxQueue7Discard2 OBJECT-TYPE
        SYNTAX       Counter64
        MAX-ACCESS   read-only
        STATUS       current
        DESCRIPTION  
            "RMON 1day TX Queue7 Discard. If the equipment is running on 4
            class QoS mode. The value of this object is always 0."
        ::= { rmon1dayPort2Entry 81 }

    rmon1dayHCTxQueue7Discard2Status OBJECT-TYPE
        SYNTAX       IpeStatsInfo
        MAX-ACCESS   read-only
        STATUS       current
        DESCRIPTION  
            "RMON 1day TX Queue7 Discard Status. 'invalid' means the
            corresponding monitoring value is not reliable because of the
            alarm or other reasons. 'maintenance' means that some maintenance
            functions are executed on the current interval."
        ::= { rmon1dayPort2Entry 82 }

    rmon1dayTxEthStatsOversizePkts2 OBJECT-TYPE
        SYNTAX       Counter32
        MAX-ACCESS   read-only
        STATUS       current
        DESCRIPTION  "RMON 1day TX Oversize Pkts."
        ::= { rmon1dayPort2Entry 83 }

    rmon1dayTxEthStatsOversizePkts2Status OBJECT-TYPE
        SYNTAX       IpeStatsInfo
        MAX-ACCESS   read-only
        STATUS       current
        DESCRIPTION  
            "RMON 1day TX Oversize Pkts Status. 'invalid' means the
            corresponding monitoring value is not reliable because of the
            alarm or other reasons. 'maintenance' means that some maintenance
            functions are executed on the current interval."
        ::= { rmon1dayPort2Entry 84 }

    rmon1dayHCTxFilterDiscard2 OBJECT-TYPE
        SYNTAX       Counter64
        MAX-ACCESS   read-only
        STATUS       current
        DESCRIPTION  "RMON 1day TX Filter Discard."
        ::= { rmon1dayPort2Entry 85 }

    rmon1dayHCTxFilterDiscard2Status OBJECT-TYPE
        SYNTAX       IpeStatsInfo
        MAX-ACCESS   read-only
        STATUS       current
        DESCRIPTION  
            "RMON 1day TX Filter Discard Status. 'invalid' means the
            corresponding monitoring value is not reliable because of the
            alarm or other reasons. 'maintenance' means that some maintenance
            functions are executed on the current interval."
        ::= { rmon1dayPort2Entry 86 }

    rmon1daySfpDataTable OBJECT-TYPE
        SYNTAX       SEQUENCE OF Rmon1daySfpDataEntry
        MAX-ACCESS   not-accessible
        STATUS       current
        DESCRIPTION  "1day ETH Port Sfp Tx/Rx Power Monitoring Table"
        ::= { rmon1dayportGroup 3 }

    rmon1daySfpDataEntry OBJECT-TYPE
        SYNTAX       Rmon1daySfpDataEntry
        MAX-ACCESS   not-accessible
        STATUS       current
        DESCRIPTION  ""
        INDEX        { rmon1daySfpDataIfIndex }
        ::= { rmon1daySfpDataTable 1 }

    Rmon1daySfpDataEntry ::= SEQUENCE {
        rmon1daySfpDataIfIndex            InterfaceIndex,
        rmon1daySfpDataNEAddress          IpAddress,
        rmon1daySfpTxPowerDataStatusInfo  IpeStatsInfo,
        rmon1daySfpTxPowerData            DisplayString,
        rmon1daySfpRxPowerDataStatusInfo  IpeStatsInfo,
        rmon1daySfpRxPowerData            DisplayString
    }

    rmon1daySfpDataIfIndex OBJECT-TYPE
        SYNTAX       InterfaceIndex
        MAX-ACCESS   not-accessible
        STATUS       current
        DESCRIPTION  "Index of this table."
        ::= { rmon1daySfpDataEntry 1 }

    rmon1daySfpDataNEAddress OBJECT-TYPE
        SYNTAX       IpAddress
        MAX-ACCESS   not-accessible
        STATUS       current
        DESCRIPTION  "reserved"
        ::= { rmon1daySfpDataEntry 2 }

    rmon1daySfpTxPowerDataStatusInfo OBJECT-TYPE
        SYNTAX       IpeStatsInfo
        MAX-ACCESS   read-only
        STATUS       current
        DESCRIPTION  "1day ETH Port Sfp Tx Power."
        ::= { rmon1daySfpDataEntry 3 }

    rmon1daySfpTxPowerData OBJECT-TYPE
        SYNTAX       DisplayString
        MAX-ACCESS   read-only
        STATUS       current
        DESCRIPTION  "1day ETH Port Sfp Tx Power Status."
        ::= { rmon1daySfpDataEntry 4 }

    rmon1daySfpRxPowerDataStatusInfo OBJECT-TYPE
        SYNTAX       IpeStatsInfo
        MAX-ACCESS   read-only
        STATUS       current
        DESCRIPTION  "1day ETH Port Sfp Rx Power."
        ::= { rmon1daySfpDataEntry 5 }

    rmon1daySfpRxPowerData OBJECT-TYPE
        SYNTAX       DisplayString
        MAX-ACCESS   read-only
        STATUS       current
        DESCRIPTION  "1day ETH Port Sfp Rx Power Status."
        ::= { rmon1daySfpDataEntry 6 }

    rmon15minVlanGroup OBJECT IDENTIFIER
        ::= { rmonEthGroup 3 }

    rmon15minVlanTable OBJECT-TYPE
        SYNTAX       SEQUENCE OF Rmon15minVlanEntry
        MAX-ACCESS   not-accessible
        STATUS       current
        DESCRIPTION  "RMON 15min VLAN Counter Table."
        ::= { rmon15minVlanGroup 1 }

    rmon15minVlanEntry OBJECT-TYPE
        SYNTAX       Rmon15minVlanEntry
        MAX-ACCESS   not-accessible
        STATUS       current
        DESCRIPTION  ""
        INDEX        { rmon15minVlanCounterIndex }
        ::= { rmon15minVlanTable 1 }

    Rmon15minVlanEntry ::= SEQUENCE {
        rmon15minVlanCounterIndex               Integer32,
        rmon15minVlanCounterNEAddress           IpAddress,
        rmon15minHCRxFrame                      Counter64,
        rmon15minHCRxFrameStatusInfo            INTEGER,
        rmon15minHCTxFrame                      Counter64,
        rmon15minHCTxFrameStatusInfo            INTEGER,
        rmon15minHCRxQoSDiscardFrame            Counter64,
        rmon15minHCRxQoSDiscardFrameStatusInfo  INTEGER,
        rmon15minHCRxOctets                     Counter64,
        rmon15minHCRxOctetsStatus               IpeStatsInfo,
        rmon15minHCTxOctets                     Counter64,
        rmon15minHCTxOctetsStatus               IpeStatsInfo
    }

    rmon15minVlanCounterIndex OBJECT-TYPE
        SYNTAX       Integer32 (1..256)
        MAX-ACCESS   not-accessible
        STATUS       current
        DESCRIPTION  
            "Index of this table.
            value range : 1 -   8 (iPASOLINK200/400/1000series/EX/iX)
                        : 1 - 256 (iPASOLINK VR 1/VR 2/VR 4/VR 10)"
        ::= { rmon15minVlanEntry 1 }

    rmon15minVlanCounterNEAddress OBJECT-TYPE
        SYNTAX       IpAddress
        MAX-ACCESS   not-accessible
        STATUS       current
        DESCRIPTION  "reserved."
        ::= { rmon15minVlanEntry 2 }

    rmon15minHCRxFrame OBJECT-TYPE
        SYNTAX       Counter64
        MAX-ACCESS   read-only
        STATUS       current
        DESCRIPTION  "RMON 15min VLAN RX Frames"
        ::= { rmon15minVlanEntry 3 }

    rmon15minHCRxFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION  
            "RMON 15min VLAN RX Frames Status. 'invalid' means the
            corresponding monitoring value is not reliable because of the
            alarm or other reasons. 'maintenance' means that some maintenance
            functions are executed on the current interval."
        ::= { rmon15minVlanEntry 4 }

    rmon15minHCTxFrame OBJECT-TYPE
        SYNTAX       Counter64
        MAX-ACCESS   read-only
        STATUS       current
        DESCRIPTION  "RMON 15min VLAN TX Frames"
        ::= { rmon15minVlanEntry 5 }

    rmon15minHCTxFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION  
            "RMON 15min VLAN TX Frames Status. 'invalid' means the
            corresponding monitoring value is not reliable because of the
            alarm or other reasons. 'maintenance' means that some maintenance
            functions are executed on the current interval."
        ::= { rmon15minVlanEntry 6 }

    rmon15minHCRxQoSDiscardFrame OBJECT-TYPE
        SYNTAX       Counter64
        MAX-ACCESS   read-only
        STATUS       current
        DESCRIPTION  "RMON 15min RX QoS Discard Frames"
        ::= { rmon15minVlanEntry 7 }

    rmon15minHCRxQoSDiscardFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION  
            "RMON 15min RX QoS Discard Frames Status. 'invalid' means the
            corresponding monitoring value is not reliable because of the
            alarm or other reasons. 'maintenance' means that some maintenance
            functions are executed on the current interval."
        ::= { rmon15minVlanEntry 8 }

    rmon15minHCRxOctets OBJECT-TYPE
        SYNTAX       Counter64
        MAX-ACCESS   read-only
        STATUS       current
        DESCRIPTION  "RMON 15min RX Octs"
        ::= { rmon15minVlanEntry 9 }

    rmon15minHCRxOctetsStatus OBJECT-TYPE
        SYNTAX       IpeStatsInfo
        MAX-ACCESS   read-only
        STATUS       current
        DESCRIPTION  
            "RMON 15min RX Octs Status. 'invalid' means the corresponding
            monitoring value is not reliable because of the alarm or other
            reasons. 'maintenance' means that some maintenance functions are
            executed on the current interval."
        ::= { rmon15minVlanEntry 10 }

    rmon15minHCTxOctets OBJECT-TYPE
        SYNTAX       Counter64
        MAX-ACCESS   read-only
        STATUS       current
        DESCRIPTION  "RMON 15min TX Octs"
        ::= { rmon15minVlanEntry 11 }

    rmon15minHCTxOctetsStatus OBJECT-TYPE
        SYNTAX       IpeStatsInfo
        MAX-ACCESS   read-only
        STATUS       current
        DESCRIPTION  
            "RMON 15min TX Octs Status. 'invalid' means the corresponding
            monitoring value is not reliable because of the alarm or other
            reasons. 'maintenance' means that some maintenance functions are
            executed on the current interval."
        ::= { rmon15minVlanEntry 12 }

    rmon15minVlanPortMappingTable OBJECT-TYPE
        SYNTAX       SEQUENCE OF Rmon15minVlanPortMappingEntry
        MAX-ACCESS   not-accessible
        STATUS       current
        DESCRIPTION  
            "If the VLAN Counter is enabled to the port, this object will
            show the corresponding VLAN Counter Index."
        ::= { rmon15minVlanGroup 2 }

    rmon15minVlanPortMappingEntry OBJECT-TYPE
        SYNTAX       Rmon15minVlanPortMappingEntry
        MAX-ACCESS   not-accessible
        STATUS       current
        DESCRIPTION  ""
        INDEX        {
                         rmon15minVlanPortMappingIfIndex,
                         rmon15minVlanMappingVlanIndex
                     }
        ::= { rmon15minVlanPortMappingTable 1 }

    Rmon15minVlanPortMappingEntry ::= SEQUENCE {
        rmon15minVlanPortMappingIfIndex  InterfaceIndex,
        rmon15minVlanMappingVlanIndex    Integer32,
        rmon15minVlanMappingNEAddress    IpAddress,
        rmon15minVlanCounterId           Integer32
    }

    rmon15minVlanPortMappingIfIndex OBJECT-TYPE
        SYNTAX       InterfaceIndex
        MAX-ACCESS   not-accessible
        STATUS       current
        DESCRIPTION  "Index of this table."
        ::= { rmon15minVlanPortMappingEntry 1 }

    rmon15minVlanMappingVlanIndex OBJECT-TYPE
        SYNTAX       Integer32 (1..4094)
        MAX-ACCESS   not-accessible
        STATUS       current
        DESCRIPTION  "VLAN ID enabling VLAN Counter"
        ::= { rmon15minVlanPortMappingEntry 2 }

    rmon15minVlanMappingNEAddress OBJECT-TYPE
        SYNTAX       IpAddress
        MAX-ACCESS   not-accessible
        STATUS       current
        DESCRIPTION  "reserved."
        ::= { rmon15minVlanPortMappingEntry 3 }

    rmon15minVlanCounterId OBJECT-TYPE
        SYNTAX       Integer32 (1..256)
        MAX-ACCESS   read-only
        STATUS       current
        DESCRIPTION  
            "VLAN Counter ID which is assigned to the port.
            value range : 1 -   8 (iPASOLINK200/400/1000series/EX/iX)
                        : 1 - 256 (iPASOLINK VR 2/VR 4/VR 10)"
        ::= { rmon15minVlanPortMappingEntry 4 }

    rmon15minVlanGroupTable OBJECT-TYPE
        SYNTAX       SEQUENCE OF Rmon15minVlanGroupEntry
        MAX-ACCESS   not-accessible
        STATUS       current
        DESCRIPTION  "RMON 15min VLAN Group Counter Table."
        ::= { rmon15minVlanGroup 3 }

    rmon15minVlanGroupEntry OBJECT-TYPE
        SYNTAX       Rmon15minVlanGroupEntry
        MAX-ACCESS   not-accessible
        STATUS       current
        DESCRIPTION  ""
        INDEX        { rmon15minVlanGroupCounterIndex }
        ::= { rmon15minVlanGroupTable 1 }

    Rmon15minVlanGroupEntry ::= SEQUENCE {
        rmon15minVlanGroupCounterIndex        Integer32,
        rmon15minVlanGroupCounterNEAddress    IpAddress,
        rmon15minVGRxFrame                    Counter64,
        rmon15minVGRxFrameStatusInfo          IpeStatsInfo,
        rmon15minVGTxFrame                    Counter64,
        rmon15minVGTxFrameStatusInfo          IpeStatsInfo,
        rmon15minVGRxOctets                   Counter64,
        rmon15minVGRxOctetsStatus             IpeStatsInfo,
        rmon15minVGTxOctets                   Counter64,
        rmon15minVGTxOctetsStatus             IpeStatsInfo,
        rmon15minVGTxQueue0Discard            Counter64,
        rmon15minVGTxQueue0DiscardStatusInfo  IpeStatsInfo,
        rmon15minVGTxQueue1Discard            Counter64,
        rmon15minVGTxQueue1DiscardStatusInfo  IpeStatsInfo,
        rmon15minVGTxQueue2Discard            Counter64,
        rmon15minVGTxQueue2DiscardStatusInfo  IpeStatsInfo,
        rmon15minVGTxQueue3Discard            Counter64,
        rmon15minVGTxQueue3DiscardStatusInfo  IpeStatsInfo,
        rmon15minVGTxQueue4Discard            Counter64,
        rmon15minVGTxQueue4DiscardStatusInfo  IpeStatsInfo,
        rmon15minVGTxQueue5Discard            Counter64,
        rmon15minVGTxQueue5DiscardStatusInfo  IpeStatsInfo,
        rmon15minVGTxQueue6Discard            Counter64,
        rmon15minVGTxQueue6DiscardStatusInfo  IpeStatsInfo,
        rmon15minVGTxQueue7Discard            Counter64,
        rmon15minVGTxQueue7DiscardStatusInfo  IpeStatsInfo
    }

    rmon15minVlanGroupCounterIndex OBJECT-TYPE
        SYNTAX       Integer32 (1..64)
        MAX-ACCESS   not-accessible
        STATUS       current
        DESCRIPTION  "Index of this table."
        ::= { rmon15minVlanGroupEntry 1 }

    rmon15minVlanGroupCounterNEAddress OBJECT-TYPE
        SYNTAX       IpAddress
        MAX-ACCESS   not-accessible
        STATUS       current
        DESCRIPTION  "reserved."
        ::= { rmon15minVlanGroupEntry 2 }

    rmon15minVGRxFrame OBJECT-TYPE
        SYNTAX       Counter64
        MAX-ACCESS   read-only
        STATUS       obsolete
        DESCRIPTION  "RMON 15min RX Frames"
        ::= { rmon15minVlanGroupEntry 3 }

    rmon15minVGRxFrameStatusInfo OBJECT-TYPE
        SYNTAX       IpeStatsInfo
        MAX-ACCESS   read-only
        STATUS       obsolete
        DESCRIPTION  
            "RMON 15min RX Frames Status. 'invalid' means the corresponding
            monitoring value is not reliable because of the alarm or other
            reasons. 'maintenance' means that some maintenance functions are
            executed on the current interval."
        ::= { rmon15minVlanGroupEntry 4 }

    rmon15minVGTxFrame OBJECT-TYPE
        SYNTAX       Counter64
        MAX-ACCESS   read-only
        STATUS       current
        DESCRIPTION  "RMON 15min TX Frames"
        ::= { rmon15minVlanGroupEntry 5 }

    rmon15minVGTxFrameStatusInfo OBJECT-TYPE
        SYNTAX       IpeStatsInfo
        MAX-ACCESS   read-only
        STATUS       current
        DESCRIPTION  
            "RMON 15min TX Frames Status. 'invalid' means the corresponding
            monitoring value is not reliable because of the alarm or other
            reasons. 'maintenance' means that some maintenance functions are
            executed on the current interval."
        ::= { rmon15minVlanGroupEntry 6 }

    rmon15minVGRxOctets OBJECT-TYPE
        SYNTAX       Counter64
        MAX-ACCESS   read-only
        STATUS       obsolete
        DESCRIPTION  "RMON 15min RX Octs"
        ::= { rmon15minVlanGroupEntry 7 }

    rmon15minVGRxOctetsStatus OBJECT-TYPE
        SYNTAX       IpeStatsInfo
        MAX-ACCESS   read-only
        STATUS       obsolete
        DESCRIPTION  
            "RMON 15min RX Octs Status. 'invalid' means the corresponding
            monitoring value is not reliable because of the alarm or other
            reasons. 'maintenance' means that some maintenance functions are
            executed on the current interval."
        ::= { rmon15minVlanGroupEntry 8 }

    rmon15minVGTxOctets OBJECT-TYPE
        SYNTAX       Counter64
        MAX-ACCESS   read-only
        STATUS       current
        DESCRIPTION  "RMON 15min TX Octs"
        ::= { rmon15minVlanGroupEntry 9 }

    rmon15minVGTxOctetsStatus OBJECT-TYPE
        SYNTAX       IpeStatsInfo
        MAX-ACCESS   read-only
        STATUS       current
        DESCRIPTION  
            "RMON 15min TX Octs Status. 'invalid' means the corresponding
            monitoring value is not reliable because of the alarm or other
            reasons. 'maintenance' means that some maintenance functions are
            executed on the current interval."
        ::= { rmon15minVlanGroupEntry 10 }

    rmon15minVGTxQueue0Discard OBJECT-TYPE
        SYNTAX       Counter64
        MAX-ACCESS   read-only
        STATUS       current
        DESCRIPTION  "RMON 15min TX Queue0 Discard"
        ::= { rmon15minVlanGroupEntry 11 }

    rmon15minVGTxQueue0DiscardStatusInfo OBJECT-TYPE
        SYNTAX       IpeStatsInfo
        MAX-ACCESS   read-only
        STATUS       current
        DESCRIPTION  
            "RMON 15min TX Queue0 Discard Status. 'invalid' means the
            corresponding monitoring value is not reliable because of the
            alarm or other reasons. 'maintenance' means that some maintenance
            functions are executed on the current interval."
        ::= { rmon15minVlanGroupEntry 12 }

    rmon15minVGTxQueue1Discard OBJECT-TYPE
        SYNTAX       Counter64
        MAX-ACCESS   read-only
        STATUS       current
        DESCRIPTION  "RMON 15min TX Queue1 Discard"
        ::= { rmon15minVlanGroupEntry 13 }

    rmon15minVGTxQueue1DiscardStatusInfo OBJECT-TYPE
        SYNTAX       IpeStatsInfo
        MAX-ACCESS   read-only
        STATUS       current
        DESCRIPTION  
            "RMON 15min TX Queue1 Discard Status. 'invalid' means the
            corresponding monitoring value is not reliable because of the
            alarm or other reasons. 'maintenance' means that some maintenance
            functions are executed on the current interval."
        ::= { rmon15minVlanGroupEntry 14 }

    rmon15minVGTxQueue2Discard OBJECT-TYPE
        SYNTAX       Counter64
        MAX-ACCESS   read-only
        STATUS       current
        DESCRIPTION  "RMON 15min TX Queue2 Discard"
        ::= { rmon15minVlanGroupEntry 15 }

    rmon15minVGTxQueue2DiscardStatusInfo OBJECT-TYPE
        SYNTAX       IpeStatsInfo
        MAX-ACCESS   read-only
        STATUS       current
        DESCRIPTION  
            "RMON 15min TX Queue2 Discard Status. 'invalid' means the
            corresponding monitoring value is not reliable because of the
            alarm or other reasons. 'maintenance' means that some maintenance
            functions are executed on the current interval."
        ::= { rmon15minVlanGroupEntry 16 }

    rmon15minVGTxQueue3Discard OBJECT-TYPE
        SYNTAX       Counter64
        MAX-ACCESS   read-only
        STATUS       current
        DESCRIPTION  "RMON 15min TX Queue3 Discard"
        ::= { rmon15minVlanGroupEntry 17 }

    rmon15minVGTxQueue3DiscardStatusInfo OBJECT-TYPE
        SYNTAX       IpeStatsInfo
        MAX-ACCESS   read-only
        STATUS       current
        DESCRIPTION  
            "RMON 15min TX Queue3 Discard Status. 'invalid' means the
            corresponding monitoring value is not reliable because of the
            alarm or other reasons. 'maintenance' means that some maintenance
            functions are executed on the current interval."
        ::= { rmon15minVlanGroupEntry 18 }

    rmon15minVGTxQueue4Discard OBJECT-TYPE
        SYNTAX       Counter64
        MAX-ACCESS   read-only
        STATUS       current
        DESCRIPTION  
            "RMON 15min TX Queue4 Discard. If the equipment is running on 4
            class QoS mode. The value of this object is always 0."
        ::= { rmon15minVlanGroupEntry 19 }

    rmon15minVGTxQueue4DiscardStatusInfo OBJECT-TYPE
        SYNTAX       IpeStatsInfo
        MAX-ACCESS   read-only
        STATUS       current
        DESCRIPTION  
            "RMON 15min TX Queue4 Discard Status. 'invalid' means the
            corresponding monitoring value is not reliable because of the
            alarm or other reasons. 'maintenance' means that some maintenance
            functions are executed on the current interval."
        ::= { rmon15minVlanGroupEntry 20 }

    rmon15minVGTxQueue5Discard OBJECT-TYPE
        SYNTAX       Counter64
        MAX-ACCESS   read-only
        STATUS       current
        DESCRIPTION  
            "RMON 15min TX Queue5 Discard. If the equipment is running on 4
            class QoS mode. The value of this object is always 0."
        ::= { rmon15minVlanGroupEntry 21 }

    rmon15minVGTxQueue5DiscardStatusInfo OBJECT-TYPE
        SYNTAX       IpeStatsInfo
        MAX-ACCESS   read-only
        STATUS       current
        DESCRIPTION  
            "RMON 15min TX Queue5 Discard Status. 'invalid' means the
            corresponding monitoring value is not reliable because of the
            alarm or other reasons. 'maintenance' means that some maintenance
            functions are executed on the current interval."
        ::= { rmon15minVlanGroupEntry 22 }

    rmon15minVGTxQueue6Discard OBJECT-TYPE
        SYNTAX       Counter64
        MAX-ACCESS   read-only
        STATUS       current
        DESCRIPTION  
            "RMON 15min TX Queue6 Discard. If the equipment is running on 4
            class QoS mode. The value of this object is always 0."
        ::= { rmon15minVlanGroupEntry 23 }

    rmon15minVGTxQueue6DiscardStatusInfo OBJECT-TYPE
        SYNTAX       IpeStatsInfo
        MAX-ACCESS   read-only
        STATUS       current
        DESCRIPTION  
            "RMON 15min TX Queue6 Discard Status. 'invalid' means the
            corresponding monitoring value is not reliable because of the
            alarm or other reasons. 'maintenance' means that some maintenance
            functions are executed on the current interval."
        ::= { rmon15minVlanGroupEntry 24 }

    rmon15minVGTxQueue7Discard OBJECT-TYPE
        SYNTAX       Counter64
        MAX-ACCESS   read-only
        STATUS       current
        DESCRIPTION  
            "RMON 15min TX Queue7 Discard. If the equipment is running on 4
            class QoS mode. The value of this object is always 0."
        ::= { rmon15minVlanGroupEntry 25 }

    rmon15minVGTxQueue7DiscardStatusInfo OBJECT-TYPE
        SYNTAX       IpeStatsInfo
        MAX-ACCESS   read-only
        STATUS       current
        DESCRIPTION  
            "RMON 15min TX Queue7 Discard Status. 'invalid' means the
            corresponding monitoring value is not reliable because of the
            alarm or other reasons. 'maintenance' means that some maintenance
            functions are executed on the current interval."
        ::= { rmon15minVlanGroupEntry 26 }

    rmon1dayVlanGroup OBJECT IDENTIFIER
        ::= { rmonEthGroup 4 }

    rmon1dayVlanTable OBJECT-TYPE
        SYNTAX       SEQUENCE OF Rmon1dayVlanEntry
        MAX-ACCESS   not-accessible
        STATUS       current
        DESCRIPTION  "RMON 1day VLAN Counter Table."
        ::= { rmon1dayVlanGroup 1 }

    rmon1dayVlanEntry OBJECT-TYPE
        SYNTAX       Rmon1dayVlanEntry
        MAX-ACCESS   not-accessible
        STATUS       current
        DESCRIPTION  ""
        INDEX        { rmon1dayVlanCounterIndex }
        ::= { rmon1dayVlanTable 1 }

    Rmon1dayVlanEntry ::= SEQUENCE {
        rmon1dayVlanCounterIndex               Integer32,
        rmon1dayVlanCounterNEAddress           IpAddress,
        rmon1dayHCRxFrame                      Counter64,
        rmon1dayHCRxFrameStatusInfo            INTEGER,
        rmon1dayHCTxFrame                      Counter64,
        rmon1dayHCTxFrameStatusInfo            INTEGER,
        rmon1dayHCRxQoSDiscardFrame            Counter64,
        rmon1dayHCRxQoSDiscardFrameStatusInfo  INTEGER,
        rmon1dayHCRxOctets                     Counter64,
        rmon1dayHCRxOctetsStatus               IpeStatsInfo,
        rmon1dayHCTxOctets                     Counter64,
        rmon1dayHCTxOctetsStatus               IpeStatsInfo
    }

    rmon1dayVlanCounterIndex OBJECT-TYPE
        SYNTAX       Integer32 (1..256)
        MAX-ACCESS   not-accessible
        STATUS       current
        DESCRIPTION  
            "Index of this table.
            value range : 1 -   8 (iPASOLINK200/400/1000series/EX/iX)
                        : 1 - 256 (iPASOLINK VR 1/VR 2/VR 4/VR 10)"
        ::= { rmon1dayVlanEntry 1 }

    rmon1dayVlanCounterNEAddress OBJECT-TYPE
        SYNTAX       IpAddress
        MAX-ACCESS   not-accessible
        STATUS       current
        DESCRIPTION  "reserved."
        ::= { rmon1dayVlanEntry 2 }

    rmon1dayHCRxFrame OBJECT-TYPE
        SYNTAX       Counter64
        MAX-ACCESS   read-only
        STATUS       current
        DESCRIPTION  "RMON 1day VLAN RX Frames"
        ::= { rmon1dayVlanEntry 3 }

    rmon1dayHCRxFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION  
            "RMON 1day VLAN RX Frames Status. 'invalid' means the
            corresponding monitoring value is not reliable because of the
            alarm or other reasons. 'maintenance' means that some maintenance
            functions are executed on the current interval."
        ::= { rmon1dayVlanEntry 4 }

    rmon1dayHCTxFrame OBJECT-TYPE
        SYNTAX       Counter64
        MAX-ACCESS   read-only
        STATUS       current
        DESCRIPTION  "RMON 1day VLAN TX Frames"
        ::= { rmon1dayVlanEntry 5 }

    rmon1dayHCTxFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION  
            "RMON 1day VLAN TX Frames Status. 'invalid' means the
            corresponding monitoring value is not reliable because of the
            alarm or other reasons. 'maintenance' means that some maintenance
            functions are executed on the current interval."
        ::= { rmon1dayVlanEntry 6 }

    rmon1dayHCRxQoSDiscardFrame OBJECT-TYPE
        SYNTAX       Counter64
        MAX-ACCESS   read-only
        STATUS       current
        DESCRIPTION  "RMON 1day RX QoS Discard Frames"
        ::= { rmon1dayVlanEntry 7 }

    rmon1dayHCRxQoSDiscardFrameStatusInfo OBJECT-TYPE
        SYNTAX       INTEGER {
                         invalid(0),
                         valid-no-maintenance(1),
                         valid-maintenance(2),
                         invalid-no-maintenance(3),
                         invalid-maintenance(4)
                     }
        MAX-ACCESS   read-only
        STATUS       current
        DESCRIPTION  
            "RMON 1day RX QoS Discard Frames Status. 'invalid' means the
            corresponding monitoring value is not reliable because of the
            alarm or other reasons. 'maintenance' means that some maintenance
            functions are executed on the current interval."
        ::= { rmon1dayVlanEntry 8 }

    rmon1dayHCRxOctets OBJECT-TYPE
        SYNTAX       Counter64
        MAX-ACCESS   read-only
        STATUS       current
        DESCRIPTION  "RMON 1day RX Octs"
        ::= { rmon1dayVlanEntry 9 }

    rmon1dayHCRxOctetsStatus OBJECT-TYPE
        SYNTAX       IpeStatsInfo
        MAX-ACCESS   read-only
        STATUS       current
        DESCRIPTION  
            "RMON 1day RX Octs Status. 'invalid' means the corresponding
            monitoring value is not reliable because of the alarm or other
            reasons. 'maintenance' means that some maintenance functions are
            executed on the current interval."
        ::= { rmon1dayVlanEntry 10 }

    rmon1dayHCTxOctets OBJECT-TYPE
        SYNTAX       Counter64
        MAX-ACCESS   read-only
        STATUS       current
        DESCRIPTION  "RMON 1day TX Octs"
        ::= { rmon1dayVlanEntry 11 }

    rmon1dayHCTxOctetsStatus OBJECT-TYPE
        SYNTAX       IpeStatsInfo
        MAX-ACCESS   read-only
        STATUS       current
        DESCRIPTION  
            "RMON 1day TX Octs Status. 'invalid' means the corresponding
            monitoring value is not reliable because of the alarm or other
            reasons. 'maintenance' means that some maintenance functions are
            executed on the current interval."
        ::= { rmon1dayVlanEntry 12 }

    rmon1dayVlanPortMappingTable OBJECT-TYPE
        SYNTAX       SEQUENCE OF Rmon1dayVlanPortMappingEntry
        MAX-ACCESS   not-accessible
        STATUS       current
        DESCRIPTION  
            "If the VLAN Counter is enabled to the port, this object will
            show the corresponding VLAN Counter Index."
        ::= { rmon1dayVlanGroup 2 }

    rmon1dayVlanPortMappingEntry OBJECT-TYPE
        SYNTAX       Rmon1dayVlanPortMappingEntry
        MAX-ACCESS   not-accessible
        STATUS       current
        DESCRIPTION  ""
        INDEX        {
                         rmon1dayVlanPortMappingIfIndex,
                         rmon1dayVlanMappingVlanIndex
                     }
        ::= { rmon1dayVlanPortMappingTable 1 }

    Rmon1dayVlanPortMappingEntry ::= SEQUENCE {
        rmon1dayVlanPortMappingIfIndex  InterfaceIndex,
        rmon1dayVlanMappingVlanIndex    Integer32,
        rmon1dayVlanMappingNEAddress    IpAddress,
        rmon1dayVlanCounterId           Integer32
    }

    rmon1dayVlanPortMappingIfIndex OBJECT-TYPE
        SYNTAX       InterfaceIndex
        MAX-ACCESS   not-accessible
        STATUS       current
        DESCRIPTION  "Index of this table."
        ::= { rmon1dayVlanPortMappingEntry 1 }

    rmon1dayVlanMappingVlanIndex OBJECT-TYPE
        SYNTAX       Integer32 (1..4094)
        MAX-ACCESS   not-accessible
        STATUS       current
        DESCRIPTION  "VLAN ID enabling VLAN Counter"
        ::= { rmon1dayVlanPortMappingEntry 2 }

    rmon1dayVlanMappingNEAddress OBJECT-TYPE
        SYNTAX       IpAddress
        MAX-ACCESS   not-accessible
        STATUS       current
        DESCRIPTION  "reserved."
        ::= { rmon1dayVlanPortMappingEntry 3 }

    rmon1dayVlanCounterId OBJECT-TYPE
        SYNTAX       Integer32 (1..256)
        MAX-ACCESS   read-only
        STATUS       current
        DESCRIPTION  
            "VLAN Counter ID which is assigned to the port.
            value range : 1 -   8 (iPASOLINK200/400/1000series/EX/iX)
                        : 1 - 256 (iPASOLINK VR 2/VR 4/VR 10)"
        ::= { rmon1dayVlanPortMappingEntry 4 }

    rmon1dayVlanGroupTable OBJECT-TYPE
        SYNTAX       SEQUENCE OF Rmon1dayVlanGroupEntry
        MAX-ACCESS   not-accessible
        STATUS       current
        DESCRIPTION  "RMON 1day VLAN Group Counter Table."
        ::= { rmon1dayVlanGroup 3 }

    rmon1dayVlanGroupEntry OBJECT-TYPE
        SYNTAX       Rmon1dayVlanGroupEntry
        MAX-ACCESS   not-accessible
        STATUS       current
        DESCRIPTION  ""
        INDEX        { rmon1dayVlanGroupCounterIndex }
        ::= { rmon1dayVlanGroupTable 1 }

    Rmon1dayVlanGroupEntry ::= SEQUENCE {
        rmon1dayVlanGroupCounterIndex        Integer32,
        rmon1dayVlanGroupCounterNEAddress    IpAddress,
        rmon1dayVGRxFrame                    Counter64,
        rmon1dayVGRxFrameStatusInfo          IpeStatsInfo,
        rmon1dayVGTxFrame                    Counter64,
        rmon1dayVGTxFrameStatusInfo          IpeStatsInfo,
        rmon1dayVGRxOctets                   Counter64,
        rmon1dayVGRxOctetsStatus             IpeStatsInfo,
        rmon1dayVGTxOctets                   Counter64,
        rmon1dayVGTxOctetsStatus             IpeStatsInfo,
        rmon1dayVGTxQueue0Discard            Counter64,
        rmon1dayVGTxQueue0DiscardStatusInfo  IpeStatsInfo,
        rmon1dayVGTxQueue1Discard            Counter64,
        rmon1dayVGTxQueue1DiscardStatusInfo  IpeStatsInfo,
        rmon1dayVGTxQueue2Discard            Counter64,
        rmon1dayVGTxQueue2DiscardStatusInfo  IpeStatsInfo,
        rmon1dayVGTxQueue3Discard            Counter64,
        rmon1dayVGTxQueue3DiscardStatusInfo  IpeStatsInfo,
        rmon1dayVGTxQueue4Discard            Counter64,
        rmon1dayVGTxQueue4DiscardStatusInfo  IpeStatsInfo,
        rmon1dayVGTxQueue5Discard            Counter64,
        rmon1dayVGTxQueue5DiscardStatusInfo  IpeStatsInfo,
        rmon1dayVGTxQueue6Discard            Counter64,
        rmon1dayVGTxQueue6DiscardStatusInfo  IpeStatsInfo,
        rmon1dayVGTxQueue7Discard            Counter64,
        rmon1dayVGTxQueue7DiscardStatusInfo  IpeStatsInfo
    }

    rmon1dayVlanGroupCounterIndex OBJECT-TYPE
        SYNTAX       Integer32 (1..64)
        MAX-ACCESS   not-accessible
        STATUS       current
        DESCRIPTION  "Index of this table."
        ::= { rmon1dayVlanGroupEntry 1 }

    rmon1dayVlanGroupCounterNEAddress OBJECT-TYPE
        SYNTAX       IpAddress
        MAX-ACCESS   not-accessible
        STATUS       current
        DESCRIPTION  "reserved."
        ::= { rmon1dayVlanGroupEntry 2 }

    rmon1dayVGRxFrame OBJECT-TYPE
        SYNTAX       Counter64
        MAX-ACCESS   read-only
        STATUS       obsolete
        DESCRIPTION  "RMON 1day RX Frames"
        ::= { rmon1dayVlanGroupEntry 3 }

    rmon1dayVGRxFrameStatusInfo OBJECT-TYPE
        SYNTAX       IpeStatsInfo
        MAX-ACCESS   read-only
        STATUS       obsolete
        DESCRIPTION  
            "RMON 1day RX Frames Status. 'invalid' means the corresponding
            monitoring value is not reliable because of the alarm or other
            reasons. 'maintenance' means that some maintenance functions are
            executed on the current interval."
        ::= { rmon1dayVlanGroupEntry 4 }

    rmon1dayVGTxFrame OBJECT-TYPE
        SYNTAX       Counter64
        MAX-ACCESS   read-only
        STATUS       current
        DESCRIPTION  "RMON 1day TX Frames"
        ::= { rmon1dayVlanGroupEntry 5 }

    rmon1dayVGTxFrameStatusInfo OBJECT-TYPE
        SYNTAX       IpeStatsInfo
        MAX-ACCESS   read-only
        STATUS       current
        DESCRIPTION  
            "RMON 1day TX Frames Status. 'invalid' means the corresponding
            monitoring value is not reliable because of the alarm or other
            reasons. 'maintenance' means that some maintenance functions are
            executed on the current interval."
        ::= { rmon1dayVlanGroupEntry 6 }

    rmon1dayVGRxOctets OBJECT-TYPE
        SYNTAX       Counter64
        MAX-ACCESS   read-only
        STATUS       obsolete
        DESCRIPTION  "RMON 1day RX Octs"
        ::= { rmon1dayVlanGroupEntry 7 }

    rmon1dayVGRxOctetsStatus OBJECT-TYPE
        SYNTAX       IpeStatsInfo
        MAX-ACCESS   read-only
        STATUS       obsolete
        DESCRIPTION  
            "RMON 1day RX Octs Status. 'invalid' means the corresponding
            monitoring value is not reliable because of the alarm or other
            reasons. 'maintenance' means that some maintenance functions are
            executed on the current interval."
        ::= { rmon1dayVlanGroupEntry 8 }

    rmon1dayVGTxOctets OBJECT-TYPE
        SYNTAX       Counter64
        MAX-ACCESS   read-only
        STATUS       current
        DESCRIPTION  "RMON 1day TX Octs"
        ::= { rmon1dayVlanGroupEntry 9 }

    rmon1dayVGTxOctetsStatus OBJECT-TYPE
        SYNTAX       IpeStatsInfo
        MAX-ACCESS   read-only
        STATUS       current
        DESCRIPTION  
            "RMON 1day TX Octs Status. 'invalid' means the corresponding
            monitoring value is not reliable because of the alarm or other
            reasons. 'maintenance' means that some maintenance functions are
            executed on the current interval."
        ::= { rmon1dayVlanGroupEntry 10 }

    rmon1dayVGTxQueue0Discard OBJECT-TYPE
        SYNTAX       Counter64
        MAX-ACCESS   read-only
        STATUS       current
        DESCRIPTION  "RMON 1day TX Queue0 Discard."
        ::= { rmon1dayVlanGroupEntry 11 }

    rmon1dayVGTxQueue0DiscardStatusInfo OBJECT-TYPE
        SYNTAX       IpeStatsInfo
        MAX-ACCESS   read-only
        STATUS       current
        DESCRIPTION  
            "RMON 1day TX Queue0 Discard Status. 'invalid' means the
            corresponding monitoring value is not reliable because of the
            alarm or other reasons. 'maintenance' means that some maintenance
            functions are executed on the current interval."
        ::= { rmon1dayVlanGroupEntry 12 }

    rmon1dayVGTxQueue1Discard OBJECT-TYPE
        SYNTAX       Counter64
        MAX-ACCESS   read-only
        STATUS       current
        DESCRIPTION  "RMON 1day TX Queue1 Discard."
        ::= { rmon1dayVlanGroupEntry 13 }

    rmon1dayVGTxQueue1DiscardStatusInfo OBJECT-TYPE
        SYNTAX       IpeStatsInfo
        MAX-ACCESS   read-only
        STATUS       current
        DESCRIPTION  
            "RMON 1day TX Queue1 Discard Status. 'invalid' means the
            corresponding monitoring value is not reliable because of the
            alarm or other reasons. 'maintenance' means that some maintenance
            functions are executed on the current interval."
        ::= { rmon1dayVlanGroupEntry 14 }

    rmon1dayVGTxQueue2Discard OBJECT-TYPE
        SYNTAX       Counter64
        MAX-ACCESS   read-only
        STATUS       current
        DESCRIPTION  "RMON 1day TX Queue2 Discard."
        ::= { rmon1dayVlanGroupEntry 15 }

    rmon1dayVGTxQueue2DiscardStatusInfo OBJECT-TYPE
        SYNTAX       IpeStatsInfo
        MAX-ACCESS   read-only
        STATUS       current
        DESCRIPTION  
            "RMON 1day TX Queue2 Discard Status. 'invalid' means the
            corresponding monitoring value is not reliable because of the
            alarm or other reasons. 'maintenance' means that some maintenance
            functions are executed on the current interval."
        ::= { rmon1dayVlanGroupEntry 16 }

    rmon1dayVGTxQueue3Discard OBJECT-TYPE
        SYNTAX       Counter64
        MAX-ACCESS   read-only
        STATUS       current
        DESCRIPTION  "RMON 1day TX Queue3 Discard."
        ::= { rmon1dayVlanGroupEntry 17 }

    rmon1dayVGTxQueue3DiscardStatusInfo OBJECT-TYPE
        SYNTAX       IpeStatsInfo
        MAX-ACCESS   read-only
        STATUS       current
        DESCRIPTION  
            "RMON 1day TX Queue3 Discard Status. 'invalid' means the
            corresponding monitoring value is not reliable because of the
            alarm or other reasons. 'maintenance' means that some maintenance
            functions are executed on the current interval."
        ::= { rmon1dayVlanGroupEntry 18 }

    rmon1dayVGTxQueue4Discard OBJECT-TYPE
        SYNTAX       Counter64
        MAX-ACCESS   read-only
        STATUS       current
        DESCRIPTION  
            "RMON 1day TX Queue4 Discard. If the equipment is running on 4
            class QoS mode. The value of this object is always 0."
        ::= { rmon1dayVlanGroupEntry 19 }

    rmon1dayVGTxQueue4DiscardStatusInfo OBJECT-TYPE
        SYNTAX       IpeStatsInfo
        MAX-ACCESS   read-only
        STATUS       current
        DESCRIPTION  
            "RMON 1day TX Queue4 Discard Status. 'invalid' means the
            corresponding monitoring value is not reliable because of the
            alarm or other reasons. 'maintenance' means that some maintenance
            functions are executed on the current interval."
        ::= { rmon1dayVlanGroupEntry 20 }

    rmon1dayVGTxQueue5Discard OBJECT-TYPE
        SYNTAX       Counter64
        MAX-ACCESS   read-only
        STATUS       current
        DESCRIPTION  
            "RMON 1day TX Queue5 Discard. If the equipment is running on 4
            class QoS mode. The value of this object is always 0."
        ::= { rmon1dayVlanGroupEntry 21 }

    rmon1dayVGTxQueue5DiscardStatusInfo OBJECT-TYPE
        SYNTAX       IpeStatsInfo
        MAX-ACCESS   read-only
        STATUS       current
        DESCRIPTION  
            "RMON 1day TX Queue5 Discard Status. 'invalid' means the
            corresponding monitoring value is not reliable because of the
            alarm or other reasons. 'maintenance' means that some maintenance
            functions are executed on the current interval."
        ::= { rmon1dayVlanGroupEntry 22 }

    rmon1dayVGTxQueue6Discard OBJECT-TYPE
        SYNTAX       Counter64
        MAX-ACCESS   read-only
        STATUS       current
        DESCRIPTION  
            "RMON 1day TX Queue6 Discard. If the equipment is running on 4
            class QoS mode. The value of this object is always 0."
        ::= { rmon1dayVlanGroupEntry 23 }

    rmon1dayVGTxQueue6DiscardStatusInfo OBJECT-TYPE
        SYNTAX       IpeStatsInfo
        MAX-ACCESS   read-only
        STATUS       current
        DESCRIPTION  
            "RMON 1day TX Queue6 Discard Status. 'invalid' means the
            corresponding monitoring value is not reliable because of the
            alarm or other reasons. 'maintenance' means that some maintenance
            functions are executed on the current interval."
        ::= { rmon1dayVlanGroupEntry 24 }

    rmon1dayVGTxQueue7Discard OBJECT-TYPE
        SYNTAX       Counter64
        MAX-ACCESS   read-only
        STATUS       current
        DESCRIPTION  
            "RMON 1day TX Queue7 Discard. If the equipment is running on 4
            class QoS mode. The value of this object is always 0."
        ::= { rmon1dayVlanGroupEntry 25 }

    rmon1dayVGTxQueue7DiscardStatusInfo OBJECT-TYPE
        SYNTAX       IpeStatsInfo
        MAX-ACCESS   read-only
        STATUS       current
        DESCRIPTION  
            "RMON 1day TX Queue7 Discard Status. 'invalid' means the
            corresponding monitoring value is not reliable because of the
            alarm or other reasons. 'maintenance' means that some maintenance
            functions are executed on the current interval."
        ::= { rmon1dayVlanGroupEntry 26 }

-----------------------------------------------
-- End User MIB Object Definitions
-----------------------------------------------

END
