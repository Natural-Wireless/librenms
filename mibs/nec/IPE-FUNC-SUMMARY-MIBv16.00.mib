--
-- ASN.1 MIB Definitions
-- Output Date: Fri Mar 05 09:45:19 2021
--

IPE-FUNC-SUMMARY-MIB DEFINITIONS ::= BEGIN

-----------------------------------------------
-- IMPORTS Definitions
-----------------------------------------------

    IMPORTS
        enterprises, IpAddress, NOTIFICATION-TYPE, OBJECT-TYPE
            FROM SNMPv2-SMI
        DateAndTime, TEXTUAL-CONVENTION
            FROM SNMPv2-TC;

-----------------------------------------------
-- Textual Convention Definitions
-----------------------------------------------

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    summaryGroup OBJECT IDENTIFIER
        ::= { pasoNeoIpe-common 1 }

-----------------------------------------------
-- summaryGroup Definitions
-----------------------------------------------

    maintSummaryGroup OBJECT IDENTIFIER
        ::= { summaryGroup 2 }

    maintFuncSummaryTable OBJECT-TYPE
        SYNTAX       SEQUENCE OF MaintFuncSummaryEntry
        MAX-ACCESS   not-accessible
        STATUS       current
        DESCRIPTION  
            "Represents maintenance functions which are performed under that
            agent. If the set request changing maintenance state to off is
            rejected, it is necessary to stop the function displayed as
            'executed' in this table."
        ::= { maintSummaryGroup 2 }

    maintFuncSummaryEntry OBJECT-TYPE
        SYNTAX       MaintFuncSummaryEntry
        MAX-ACCESS   not-accessible
        STATUS       current
        DESCRIPTION  ""
        INDEX        { maintFuncSummaryCategory }
        ::= { maintFuncSummaryTable 1 }

    MaintFuncSummaryEntry ::= SEQUENCE {
        maintFuncSummaryCategory     INTEGER,
        maintFuncSummaryNEAddress    IpAddress,
        maintFuncSummary             INTEGER,
        maintFuncSummaryLastUpdated  DateAndTime
    }

    maintFuncSummaryCategory OBJECT-TYPE
        SYNTAX       INTEGER {
                         modemLb(1),
                         modemMaint(2),
                         modemSwgMaint(3),
                         e1Lb1(4),
                         e1Lb2(5),
                         stm1Lb1(6),
                         stm1Lb2(7),
                         sncpControl(8),
                         timingSourceControl(9),
                         laserShutdownControl(10),
                         fileUpdate(11),
                         etherring(12),
                         dot3ah(14),
                         ptp(15),
                         etherLaserShutdownControl(19),
                         etherL2Lb1(20),
                         etherL2Lb2(21),
                         serviceSwitch(27)
                     }
        MAX-ACCESS   not-accessible
        STATUS       current
        DESCRIPTION  "Index of this table."
        ::= { maintFuncSummaryEntry 1 }

    maintFuncSummaryNEAddress OBJECT-TYPE
        SYNTAX       IpAddress
        MAX-ACCESS   not-accessible
        STATUS       current
        DESCRIPTION  "reserved."
        ::= { maintFuncSummaryEntry 2 }

    maintFuncSummary OBJECT-TYPE
        SYNTAX       INTEGER { invalid(0), none(1), executed(2) }
        MAX-ACCESS   read-only
        STATUS       current
        DESCRIPTION  
            "Maintenance function state.
            'executed' state means the function is executing under that agent
            when the get-request is processed."
        ::= { maintFuncSummaryEntry 3 }

    maintFuncSummaryLastUpdated OBJECT-TYPE
        SYNTAX       DateAndTime
        MAX-ACCESS   read-only
        STATUS       current
        DESCRIPTION  
            "The time of the function entered its state. The initial value is
            the time the agent booted."
        ::= { maintFuncSummaryEntry 4 }

-----------------------------------------------
-- End User MIB Object Definitions
-----------------------------------------------

END
