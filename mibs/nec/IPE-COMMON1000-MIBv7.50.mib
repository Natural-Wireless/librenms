--
-- ASN.1 MIB Definitions
-- Output Date: Fri Mar 05 09:44:55 2021
--

IPE-COMMON1000-MIB DEFINITIONS ::= BEGIN

-----------------------------------------------
-- IMPORTS Definitions
-----------------------------------------------

    IMPORTS
        Ipv6Address
            FROM IPV6-TC
        enterprises, Integer32, IpAddress, NOTIFICATION-TYPE, OBJECT-TYPE
            FROM SNMPv2-SMI
        DateAndTime, DisplayString, TEXTUAL-CONVENTION
            FROM SNMPv2-TC;

-----------------------------------------------
-- Textual Convention Definitions
-----------------------------------------------

    EnableDisableValue ::= TEXTUAL-CONVENTION
        STATUS       current
        DESCRIPTION  "Enable/Disable Type"
        SYNTAX       INTEGER { invalid(0), disable(1), enable(2) }

    OffOnValue ::= TEXTUAL-CONVENTION
        STATUS       current
        DESCRIPTION  "Off/On Type"
        SYNTAX       INTEGER { invalid(0), off(1), on(2) }

    SeverityValue ::= TEXTUAL-CONVENTION
        STATUS       current
        DESCRIPTION  "Severity (CCITT Rec. X.733)"
        SYNTAX       INTEGER {
                         cleared(1),
                         indetermine(2),
                         critical(3),
                         major(4),
                         minor(5),
                         warning(6),
                         notReport(7)
                     }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    system5 OBJECT IDENTIFIER
        ::= { radioEquipment 5 }

    pasoNeoIpe-common OBJECT IDENTIFIER
        ::= { radioEquipment 501 }

-----------------------------------------------
-- system5 Group Definitions
-----------------------------------------------

    ipeConfigurationGroup OBJECT IDENTIFIER
        ::= { system5 3 }

    ipeCfgPortGroup OBJECT IDENTIFIER
        ::= { ipeConfigurationGroup 15 }

    ipeCfgPortLct1kTable OBJECT-TYPE
        SYNTAX       SEQUENCE OF IpeCfgPortLct1kEntry
        MAX-ACCESS   not-accessible
        STATUS       current
        DESCRIPTION  
            "LCT port set up information table.
            TABSZ=1"
        ::= { ipeCfgPortGroup 8 }

    ipeCfgPortLct1kEntry OBJECT-TYPE
        SYNTAX       IpeCfgPortLct1kEntry
        MAX-ACCESS   not-accessible
        STATUS       current
        DESCRIPTION  "entry of  LCT port set up information table."
        INDEX        { ipeCfgPortLct1kIndex }
        ::= { ipeCfgPortLct1kTable 1 }

    IpeCfgPortLct1kEntry ::= SEQUENCE {
        ipeCfgPortLct1kIndex                   Integer32,
        ipeCfgPortLct1kNEAddress               IpAddress,
        ipeCfgPortLct1kIpAddress               IpAddress,
        ipeCfgPortLct1kNetMask                 IpAddress,
        ipeCfgPortLct1kEnable                  INTEGER,
        ipeCfgPortLct1kMtu                     Integer32,
        ipeCfgPortLct1kAutoNeg                 INTEGER,
        ipeCfgPortLct1kLinkLocalAddress        Ipv6Address,
        ipeCfgPortLct1kLinkLocalAddressOrigin  INTEGER,
        ipeCfgPortLct1kHttpReverseProxyEnable  EnableDisableValue
    }

    ipeCfgPortLct1kIndex OBJECT-TYPE
        SYNTAX       Integer32 (1..2)
        MAX-ACCESS   not-accessible
        STATUS       current
        DESCRIPTION  "Index of table."
        ::= { ipeCfgPortLct1kEntry 1 }

    ipeCfgPortLct1kNEAddress OBJECT-TYPE
        SYNTAX       IpAddress
        MAX-ACCESS   not-accessible
        STATUS       current
        DESCRIPTION  ""
        ::= { ipeCfgPortLct1kEntry 2 }

    ipeCfgPortLct1kIpAddress OBJECT-TYPE
        SYNTAX       IpAddress
        MAX-ACCESS   read-write
        STATUS       current
        DESCRIPTION  "IPaddress of LCT port."
        ::= { ipeCfgPortLct1kEntry 3 }

    ipeCfgPortLct1kNetMask OBJECT-TYPE
        SYNTAX       IpAddress
        MAX-ACCESS   read-write
        STATUS       current
        DESCRIPTION  "Subnet mask of LCT port."
        ::= { ipeCfgPortLct1kEntry 4 }

    ipeCfgPortLct1kEnable OBJECT-TYPE
        SYNTAX       INTEGER { enabled(1), disabled(2) }
        MAX-ACCESS   read-write
        STATUS       current
        DESCRIPTION  
            "Effective/invalid setting of LCT port.
            default value is 'enabled'.(iPASOLINK EX Advanced)"
        ::= { ipeCfgPortLct1kEntry 5 }

    ipeCfgPortLct1kMtu OBJECT-TYPE
        SYNTAX       Integer32 (256..1500)
        MAX-ACCESS   read-write
        STATUS       current
        DESCRIPTION  
            "MTU value of LCT.
            value range:256 to 1500"
        ::= { ipeCfgPortLct1kEntry 6 }

    ipeCfgPortLct1kAutoNeg OBJECT-TYPE
        SYNTAX       INTEGER { enabled(1), disabled(2) }
        MAX-ACCESS   read-write
        STATUS       current
        DESCRIPTION  
            "Effective/invalid setting of LCT AUTO NEGOTIATION.
            value range: enabled
                        disabled"
        ::= { ipeCfgPortLct1kEntry 7 }

    ipeCfgPortLct1kLinkLocalAddress OBJECT-TYPE
        SYNTAX       Ipv6Address
        MAX-ACCESS   read-write
        STATUS       current
        DESCRIPTION  "The IPv6 Link Local address of the LCT port."
        ::= { ipeCfgPortLct1kEntry 8 }

    ipeCfgPortLct1kLinkLocalAddressOrigin OBJECT-TYPE
        SYNTAX       INTEGER { invalid(0), manual(1), linklayer(2) }
        MAX-ACCESS   read-write
        STATUS       current
        DESCRIPTION  
            "The origin of the address.
            manual(1):
            indicates that the address was manually configured to a specified
            address, e.g., by user configuration.
            
            linklayer(2):
            indicates the address to be created by IPv6 stateless address
            auto-configuration."
        ::= { ipeCfgPortLct1kEntry 9 }

    ipeCfgPortLct1kHttpReverseProxyEnable OBJECT-TYPE
        SYNTAX       EnableDisableValue
        MAX-ACCESS   read-write
        STATUS       current
        DESCRIPTION  
            "Enables or disables HTTP Reverse proxy on this interface."
        ::= { ipeCfgPortLct1kEntry 10 }

-----------------------------------------------
-- IPE COMMON Group Definitions
-----------------------------------------------

    alarmStatusGroup OBJECT IDENTIFIER
        ::= { pasoNeoIpe-common 3 }

    inventoryGroup OBJECT IDENTIFIER
        ::= { pasoNeoIpe-common 7 }

-----------------------------------------------
-- alarmStatusGroup Definitions
-----------------------------------------------

    asMainCtrlGroup OBJECT IDENTIFIER
        ::= { alarmStatusGroup 35 }

    asMainCtrlGroupTable OBJECT-TYPE
        SYNTAX       SEQUENCE OF AsMainCtrlGroupEntry
        MAX-ACCESS   not-accessible
        STATUS       current
        DESCRIPTION  "Main card group object for iPASO1000."
        ::= { asMainCtrlGroup 1 }

    asMainCtrlGroupEntry OBJECT-TYPE
        SYNTAX       AsMainCtrlGroupEntry
        MAX-ACCESS   not-accessible
        STATUS       current
        DESCRIPTION  ""
        INDEX        { asMainCtrlGroupIndex }
        ::= { asMainCtrlGroupTable 1 }

    AsMainCtrlGroupEntry ::= SEQUENCE {
        asMainCtrlGroupIndex                 Integer32,
        asMainCtrlGroupNEAddress             IpAddress,
        ctrlGroupSvLineAlarm                 SeverityValue,
        ctrlGroupIduTotalAlarm               SeverityValue,
        ctrlGroupMaintenance                 OffOnValue,
        ctrlGroupComFail                     SeverityValue,
        ctrlGroupFirmwareVerMismatch         SeverityValue,
        ctrlGroupCardMismatch                SeverityValue,
        ctrlGroupHardwareVerMismatch         SeverityValue,
        ctrlGroupMountedClk2mMismatch        SeverityValue,
        ctrlGroupSwitchOverFailure           OffOnValue,
        ctrlGroupSwitchComplete              OffOnValue,
        ctrlGroupForcedSbySwitchComplete     OffOnValue,
        ctrlGroupSwitchedTime                DateAndTime,
        ctrlGroupSwitchedReason              DisplayString,
        ctrlGroupConfigDataStoredTime        DateAndTime,
        ctrlGroupSbyBusErrorTx               SeverityValue,
        ctrlGroupSbyBusErrorRx               SeverityValue,
        ctrlGroupSbyTermComFailAlarm         SeverityValue,
        ctrlGroupDbMismatch                  SeverityValue,
        ctrlGroupSoftkeyEquipSerialMismatch  SeverityValue,
        ctrlGroupTrapSuppressionStatus       OffOnValue,
        ctrlGroupStartupStatus               INTEGER
    }

    asMainCtrlGroupIndex OBJECT-TYPE
        SYNTAX       Integer32 (1..1)
        MAX-ACCESS   not-accessible
        STATUS       current
        DESCRIPTION  ""
        ::= { asMainCtrlGroupEntry 1 }

    asMainCtrlGroupNEAddress OBJECT-TYPE
        SYNTAX       IpAddress
        MAX-ACCESS   not-accessible
        STATUS       current
        DESCRIPTION  ""
        ::= { asMainCtrlGroupEntry 2 }

    ctrlGroupSvLineAlarm OBJECT-TYPE
        SYNTAX       SeverityValue
        MAX-ACCESS   read-only
        STATUS       obsolete
        DESCRIPTION  ""
        ::= { asMainCtrlGroupEntry 3 }

    ctrlGroupIduTotalAlarm OBJECT-TYPE
        SYNTAX       SeverityValue
        MAX-ACCESS   read-only
        STATUS       obsolete
        DESCRIPTION  ""
        ::= { asMainCtrlGroupEntry 4 }

    ctrlGroupMaintenance OBJECT-TYPE
        SYNTAX       OffOnValue
        MAX-ACCESS   read-only
        STATUS       current
        DESCRIPTION  ""
        ::= { asMainCtrlGroupEntry 5 }

    ctrlGroupComFail OBJECT-TYPE
        SYNTAX       SeverityValue
        MAX-ACCESS   read-only
        STATUS       obsolete
        DESCRIPTION  ""
        ::= { asMainCtrlGroupEntry 6 }

    ctrlGroupFirmwareVerMismatch OBJECT-TYPE
        SYNTAX       SeverityValue
        MAX-ACCESS   read-only
        STATUS       obsolete
        DESCRIPTION  ""
        ::= { asMainCtrlGroupEntry 7 }

    ctrlGroupCardMismatch OBJECT-TYPE
        SYNTAX       SeverityValue
        MAX-ACCESS   read-only
        STATUS       obsolete
        DESCRIPTION  ""
        ::= { asMainCtrlGroupEntry 8 }

    ctrlGroupHardwareVerMismatch OBJECT-TYPE
        SYNTAX       SeverityValue
        MAX-ACCESS   read-only
        STATUS       obsolete
        DESCRIPTION  ""
        ::= { asMainCtrlGroupEntry 9 }

    ctrlGroupMountedClk2mMismatch OBJECT-TYPE
        SYNTAX       SeverityValue
        MAX-ACCESS   read-only
        STATUS       obsolete
        DESCRIPTION  ""
        ::= { asMainCtrlGroupEntry 10 }

    ctrlGroupSwitchOverFailure OBJECT-TYPE
        SYNTAX       OffOnValue
        MAX-ACCESS   read-only
        STATUS       obsolete
        DESCRIPTION  ""
        ::= { asMainCtrlGroupEntry 11 }

    ctrlGroupSwitchComplete OBJECT-TYPE
        SYNTAX       OffOnValue
        MAX-ACCESS   read-only
        STATUS       obsolete
        DESCRIPTION  ""
        ::= { asMainCtrlGroupEntry 12 }

    ctrlGroupForcedSbySwitchComplete OBJECT-TYPE
        SYNTAX       OffOnValue
        MAX-ACCESS   read-only
        STATUS       obsolete
        DESCRIPTION  ""
        ::= { asMainCtrlGroupEntry 13 }

    ctrlGroupSwitchedTime OBJECT-TYPE
        SYNTAX       DateAndTime
        MAX-ACCESS   read-only
        STATUS       obsolete
        DESCRIPTION  ""
        ::= { asMainCtrlGroupEntry 14 }

    ctrlGroupSwitchedReason OBJECT-TYPE
        SYNTAX       DisplayString (SIZE(0..32))
        MAX-ACCESS   read-only
        STATUS       obsolete
        DESCRIPTION  ""
        ::= { asMainCtrlGroupEntry 15 }

    ctrlGroupConfigDataStoredTime OBJECT-TYPE
        SYNTAX       DateAndTime
        MAX-ACCESS   read-only
        STATUS       obsolete
        DESCRIPTION  ""
        ::= { asMainCtrlGroupEntry 16 }

    ctrlGroupSbyBusErrorTx OBJECT-TYPE
        SYNTAX       SeverityValue
        MAX-ACCESS   read-only
        STATUS       obsolete
        DESCRIPTION  ""
        ::= { asMainCtrlGroupEntry 17 }

    ctrlGroupSbyBusErrorRx OBJECT-TYPE
        SYNTAX       SeverityValue
        MAX-ACCESS   read-only
        STATUS       obsolete
        DESCRIPTION  ""
        ::= { asMainCtrlGroupEntry 18 }

    ctrlGroupSbyTermComFailAlarm OBJECT-TYPE
        SYNTAX       SeverityValue
        MAX-ACCESS   read-only
        STATUS       obsolete
        DESCRIPTION  ""
        ::= { asMainCtrlGroupEntry 19 }

    ctrlGroupDbMismatch OBJECT-TYPE
        SYNTAX       SeverityValue
        MAX-ACCESS   read-only
        STATUS       obsolete
        DESCRIPTION  ""
        ::= { asMainCtrlGroupEntry 20 }

    ctrlGroupSoftkeyEquipSerialMismatch OBJECT-TYPE
        SYNTAX       SeverityValue
        MAX-ACCESS   read-only
        STATUS       obsolete
        DESCRIPTION  ""
        ::= { asMainCtrlGroupEntry 21 }

    ctrlGroupTrapSuppressionStatus OBJECT-TYPE
        SYNTAX       OffOnValue
        MAX-ACCESS   read-only
        STATUS       current
        DESCRIPTION  "Trap Suppression Status"
        ::= { asMainCtrlGroupEntry 22 }

    ctrlGroupStartupStatus OBJECT-TYPE
        SYNTAX       INTEGER { powerOn(1), cpuReset(2), deviceReset(3) }
        MAX-ACCESS   read-only
        STATUS       current
        DESCRIPTION  "Main Card Startup Status."
        ::= { asMainCtrlGroupEntry 23 }

    asMainCtrlCardTable OBJECT-TYPE
        SYNTAX       SEQUENCE OF AsMainCtrlCardEntry
        MAX-ACCESS   not-accessible
        STATUS       current
        DESCRIPTION  "Main card object for iPASO1000."
        ::= { asMainCtrlGroup 2 }

    asMainCtrlCardEntry OBJECT-TYPE
        SYNTAX       AsMainCtrlCardEntry
        MAX-ACCESS   not-accessible
        STATUS       current
        DESCRIPTION  ""
        INDEX        { asMainCtrlCardIndex }
        ::= { asMainCtrlCardTable 1 }

    AsMainCtrlCardEntry ::= SEQUENCE {
        asMainCtrlCardIndex            Integer32,
        asMainCtrlCardNEAddress        IpAddress,
        mainCardAlarm                  SeverityValue,
        mainUsbFailure                 SeverityValue,
        mainCpuAlarm                   SeverityValue,
        mainMemoryFailure              SeverityValue,
        mainClk2mMount                 INTEGER,
        mainCardRunningStatus          INTEGER,
        mainTempAlarm                  SeverityValue,
        mainCtrlUnequipped             SeverityValue,
        mainCtrlBusError               SeverityValue,
        mainTemperature                Integer32,
        mainFPGAMismatch               SeverityValue,
        mainClkOptionCardUnequipped    SeverityValue,
        mainClkOptionCardTypeMismatch  SeverityValue,
        mainBbAlarm                    SeverityValue
    }

    asMainCtrlCardIndex OBJECT-TYPE
        SYNTAX       Integer32 (17..18)
        MAX-ACCESS   not-accessible
        STATUS       current
        DESCRIPTION  
            "Index of this table. value range: 17 (VR 1/VR 2/VR 4), 17-18
            (1000/VR 10)"
        ::= { asMainCtrlCardEntry 1 }

    asMainCtrlCardNEAddress OBJECT-TYPE
        SYNTAX       IpAddress
        MAX-ACCESS   not-accessible
        STATUS       current
        DESCRIPTION  ""
        ::= { asMainCtrlCardEntry 2 }

    mainCardAlarm OBJECT-TYPE
        SYNTAX       SeverityValue
        MAX-ACCESS   read-only
        STATUS       current
        DESCRIPTION  ""
        ::= { asMainCtrlCardEntry 3 }

    mainUsbFailure OBJECT-TYPE
        SYNTAX       SeverityValue
        MAX-ACCESS   read-only
        STATUS       obsolete
        DESCRIPTION  ""
        ::= { asMainCtrlCardEntry 4 }

    mainCpuAlarm OBJECT-TYPE
        SYNTAX       SeverityValue
        MAX-ACCESS   read-only
        STATUS       current
        DESCRIPTION  ""
        ::= { asMainCtrlCardEntry 5 }

    mainMemoryFailure OBJECT-TYPE
        SYNTAX       SeverityValue
        MAX-ACCESS   read-only
        STATUS       obsolete
        DESCRIPTION  ""
        ::= { asMainCtrlCardEntry 6 }

    mainClk2mMount OBJECT-TYPE
        SYNTAX       INTEGER { mount(2) }
        MAX-ACCESS   read-only
        STATUS       obsolete
        DESCRIPTION  ""
        ::= { asMainCtrlCardEntry 7 }

    mainCardRunningStatus OBJECT-TYPE
        SYNTAX       INTEGER {
                         invalid(0),
                         act(1),
                         sby(2),
                         flt(3),
                         actFlt(4),
                         sbyFlt(5),
                         init(6),
                         oos(7),
                         initFlt(8),
                         unmount(9)
                     }
        MAX-ACCESS   read-only
        STATUS       obsolete
        DESCRIPTION  ""
        ::= { asMainCtrlCardEntry 8 }

    mainTempAlarm OBJECT-TYPE
        SYNTAX       SeverityValue
        MAX-ACCESS   read-only
        STATUS       current
        DESCRIPTION  ""
        ::= { asMainCtrlCardEntry 9 }

    mainCtrlUnequipped OBJECT-TYPE
        SYNTAX       SeverityValue
        MAX-ACCESS   read-only
        STATUS       obsolete
        DESCRIPTION  ""
        ::= { asMainCtrlCardEntry 10 }

    mainCtrlBusError OBJECT-TYPE
        SYNTAX       SeverityValue
        MAX-ACCESS   read-only
        STATUS       current
        DESCRIPTION  ""
        ::= { asMainCtrlCardEntry 11 }

    mainTemperature OBJECT-TYPE
        SYNTAX       Integer32 (-999|-500..1500)
        UNITS        "0.1 degree"
        MAX-ACCESS   read-only
        STATUS       current
        DESCRIPTION  
            "Main Card Temperature.
            if the unexpected condition happened, the object reports value
            '-999'."
        ::= { asMainCtrlCardEntry 12 }

    mainFPGAMismatch OBJECT-TYPE
        SYNTAX       SeverityValue
        MAX-ACCESS   read-only
        STATUS       obsolete
        DESCRIPTION  ""
        ::= { asMainCtrlCardEntry 13 }

    mainClkOptionCardUnequipped OBJECT-TYPE
        SYNTAX       SeverityValue
        MAX-ACCESS   read-only
        STATUS       current
        DESCRIPTION  "CLK Option Card Unequipped Alarm."
        ::= { asMainCtrlCardEntry 14 }

    mainClkOptionCardTypeMismatch OBJECT-TYPE
        SYNTAX       SeverityValue
        MAX-ACCESS   read-only
        STATUS       current
        DESCRIPTION  "CLK Option Card Type Mismatch Alarm."
        ::= { asMainCtrlCardEntry 15 }

    mainBbAlarm OBJECT-TYPE
        SYNTAX       SeverityValue
        MAX-ACCESS   read-only
        STATUS       current
        DESCRIPTION  ""
        ::= { asMainCtrlCardEntry 16 }

    invClkOptionCardInfoTable OBJECT-TYPE
        SYNTAX       SEQUENCE OF InvClkOptionCardInfoEntry
        MAX-ACCESS   not-accessible
        STATUS       current
        DESCRIPTION  "Equipment Inventory Information for CLK Option Card."
        ::= { inventoryGroup 11 }

    invClkOptionCardInfoEntry OBJECT-TYPE
        SYNTAX       InvClkOptionCardInfoEntry
        MAX-ACCESS   not-accessible
        STATUS       current
        DESCRIPTION  ""
        INDEX        { invClkOptionCardInfoIndex }
        ::= { invClkOptionCardInfoTable 1 }

    InvClkOptionCardInfoEntry ::= SEQUENCE {
        invClkOptionCardInfoIndex         Integer32,
        invClkOptionCardInfoNEAddress     IpAddress,
        invClkOptionCardName              DisplayString,
        invClkOptionCardCodeNo            DisplayString,
        invClkOptionCardSerialNo          DisplayString,
        invClkOptionCardManufacturedDate  DisplayString,
        invClkOptionCardHardVersion       DisplayString
    }

    invClkOptionCardInfoIndex OBJECT-TYPE
        SYNTAX       Integer32 (1..2)
        MAX-ACCESS   not-accessible
        STATUS       current
        DESCRIPTION  
            "Index of this table. value range: 1 (VR 1/VR 2/VR 4), 1-2 (VR
            10)"
        ::= { invClkOptionCardInfoEntry 1 }

    invClkOptionCardInfoNEAddress OBJECT-TYPE
        SYNTAX       IpAddress
        MAX-ACCESS   not-accessible
        STATUS       current
        DESCRIPTION  "reserved."
        ::= { invClkOptionCardInfoEntry 2 }

    invClkOptionCardName OBJECT-TYPE
        SYNTAX       DisplayString
        MAX-ACCESS   read-only
        STATUS       current
        DESCRIPTION  "Name"
        ::= { invClkOptionCardInfoEntry 3 }

    invClkOptionCardCodeNo OBJECT-TYPE
        SYNTAX       DisplayString
        MAX-ACCESS   read-only
        STATUS       current
        DESCRIPTION  "Code No."
        ::= { invClkOptionCardInfoEntry 4 }

    invClkOptionCardSerialNo OBJECT-TYPE
        SYNTAX       DisplayString
        MAX-ACCESS   read-only
        STATUS       current
        DESCRIPTION  "Serial No."
        ::= { invClkOptionCardInfoEntry 5 }

    invClkOptionCardManufacturedDate OBJECT-TYPE
        SYNTAX       DisplayString
        MAX-ACCESS   read-only
        STATUS       current
        DESCRIPTION  "Manufactured Date"
        ::= { invClkOptionCardInfoEntry 6 }

    invClkOptionCardHardVersion OBJECT-TYPE
        SYNTAX       DisplayString
        MAX-ACCESS   read-only
        STATUS       current
        DESCRIPTION  "Hardware Version."
        ::= { invClkOptionCardInfoEntry 7 }

-----------------------------------------------
-- End User MIB Object Definitions
-----------------------------------------------

END
