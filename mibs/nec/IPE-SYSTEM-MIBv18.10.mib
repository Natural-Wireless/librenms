--
-- ASN.1 MIB Definitions
-- Output Date: Wed Nov 16 20:34:14 2022
--

IPE-SYSTEM-MIB DEFINITIONS ::= BEGIN

-----------------------------------------------
-- IMPORTS Definitions
-----------------------------------------------

    IMPORTS
        BridgeId, Timeout
            FROM BRIDGE-MIB
        InterfaceIndex
            FROM IF-MIB
        InetAddress, InetAddressPrefixLength, InetAddressType
            FROM INET-ADDRESS-MIB
        Ipv6Address
            FROM IPV6-TC
        Counter32, enterprises, Integer32, IpAddress, NOTIFICATION-TYPE,
        OBJECT-TYPE, Unsigned32
            FROM SNMPv2-SMI
        DateAndTime, DisplayString, MacAddress, PhysAddress, RowStatus,
        TEXTUAL-CONVENTION
            FROM SNMPv2-TC;

-----------------------------------------------
-- Textual Convention Definitions
-----------------------------------------------

    EnableDisableValue ::= TEXTUAL-CONVENTION
        STATUS       current
        DESCRIPTION  "Enable/Disable Type"
        SYNTAX       INTEGER { invalid(0), disable(1), enable(2) }

    IpeNtpKeyAdminIndex ::= TEXTUAL-CONVENTION
        DISPLAY-HINT "d"
        STATUS       current
        DESCRIPTION  
            "Administrative Index for NTP Key.
            This value is for just indexing and does not have any relation to
            the NTP Key Id (protocol sense)."
        SYNTAX       Integer32 (1..4)

    IpeNtpKeyAdminIndexOrZero ::= TEXTUAL-CONVENTION
        DISPLAY-HINT "d"
        STATUS       current
        DESCRIPTION  
            "Administrative Index for NTP Key.
            This value is for just indexing and does not have any relation to
            the NTP Key Id (protocol sense).
            If the value '0' is specified, the NTP authentication is not
            used."
        SYNTAX       Integer32 (0..4)

    OffOnValue ::= TEXTUAL-CONVENTION
        STATUS       current
        DESCRIPTION  "Off/On Type"
        SYNTAX       INTEGER { invalid(0), off(1), on(2) }

    UsedNotusedValue ::= TEXTUAL-CONVENTION
        STATUS       current
        DESCRIPTION  "Used/NotUsed Type"
        SYNTAX       INTEGER { invalid(0), notUsed(1), used(2) }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    system1 OBJECT IDENTIFIER
        ::= { radioEquipment 1 }

    system5 OBJECT IDENTIFIER
        ::= { radioEquipment 5 }

-----------------------------------------------
-- system1 Group Definitions
-----------------------------------------------

    pmSystem OBJECT IDENTIFIER
        ::= { system1 1 }

    sysPmType OBJECT-TYPE
        SYNTAX       INTEGER { typeBranchNE(13), typeNormal(14) }
        MAX-ACCESS   read-only
        STATUS       current
        DESCRIPTION  "PM TYPE SETTING."
        ::= { pmSystem 3 }

    sysPrimaryIpAddress OBJECT-TYPE
        SYNTAX       IpAddress
        MAX-ACCESS   read-only
        STATUS       current
        DESCRIPTION  "PRIMARY IP ADDRESS."
        ::= { pmSystem 5 }

    sysOppositeIpAddress OBJECT-TYPE
        SYNTAX       IpAddress
        MAX-ACCESS   read-only
        STATUS       current
        DESCRIPTION  "IP address of the destination."
        ::= { pmSystem 9 }

    sysEquipmentType OBJECT-TYPE
        SYNTAX       Integer32
        MAX-ACCESS   read-only
        STATUS       current
        DESCRIPTION  "Equipment Type."
        ::= { pmSystem 13 }

    sysEquipmentConfig OBJECT-TYPE
        SYNTAX       Integer32
        MAX-ACCESS   read-only
        STATUS       current
        DESCRIPTION  "Equipment Config."
        ::= { pmSystem 14 }

    sysPrimaryIpv6Address OBJECT-TYPE
        SYNTAX       Ipv6Address
        MAX-ACCESS   read-only
        STATUS       current
        DESCRIPTION  "PRIMARY IPv6 ADDRESS."
        ::= { pmSystem 105 }

    sysOppositeIpv6Address OBJECT-TYPE
        SYNTAX       Ipv6Address
        MAX-ACCESS   read-only
        STATUS       current
        DESCRIPTION  "IPv6 address of the destination."
        ::= { pmSystem 109 }

-----------------------------------------------
-- system5 Group Definitions
-----------------------------------------------

    ipeSystemGroup OBJECT IDENTIFIER
        ::= { system5 1 }

    ipeSysInfoTable OBJECT-TYPE
        SYNTAX       SEQUENCE OF IpeSysInfoEntry
        MAX-ACCESS   not-accessible
        STATUS       current
        DESCRIPTION  "Table of System Information."
        ::= { ipeSystemGroup 1 }

    ipeSysInfoEntry OBJECT-TYPE
        SYNTAX       IpeSysInfoEntry
        MAX-ACCESS   not-accessible
        STATUS       current
        DESCRIPTION  "Entry of System Information."
        INDEX        { ipeSysInfoIndex }
        ::= { ipeSysInfoTable 1 }

    IpeSysInfoEntry ::= SEQUENCE {
        ipeSysInfoIndex                       Integer32,
        ipeSysInfoNEAddress                   IpAddress,
        ipeSysNeName                          DisplayString,
        ipeSysAreaName                        DisplayString,
        ipeSysNote                            DisplayString,
        ipeSysPrimaryIpAddress                IpAddress,
        ipeSysSubnetMask                      IpAddress,
        ipeSysDefaultGateway                  IpAddress,
        ipeSysMacAddress                      MacAddress,
        ipeSysMibVersion                      DisplayString,
        ipeSysEquipmentType                   Integer32,
        ipeSysPmType                          Integer32,
        ipeSysPrimaryIpv6Address              Ipv6Address,
        ipeSysPrimaryIpv6AddressPrefixLength  InetAddressPrefixLength,
        ipeSysIpv6DefaultGateway              Ipv6Address,
        ipeSysIpv6DefaultGatewayIfIndex       INTEGER,
        ipeSysPrimaryIfIndex                  INTEGER,
        ipeSysIpv4DropFilterEnable            EnableDisableValue
    }

    ipeSysInfoIndex OBJECT-TYPE
        SYNTAX       Integer32 (1..1)
        MAX-ACCESS   not-accessible
        STATUS       current
        DESCRIPTION  "Index of Table."
        ::= { ipeSysInfoEntry 1 }

    ipeSysInfoNEAddress OBJECT-TYPE
        SYNTAX       IpAddress
        MAX-ACCESS   not-accessible
        STATUS       current
        DESCRIPTION  ""
        ::= { ipeSysInfoEntry 2 }

    ipeSysNeName OBJECT-TYPE
        SYNTAX       DisplayString
        MAX-ACCESS   read-only
        STATUS       current
        DESCRIPTION  "Equipment name (for display)."
        ::= { ipeSysInfoEntry 3 }

    ipeSysAreaName OBJECT-TYPE
        SYNTAX       DisplayString
        MAX-ACCESS   read-only
        STATUS       current
        DESCRIPTION  "Area name (for display)."
        ::= { ipeSysInfoEntry 4 }

    ipeSysNote OBJECT-TYPE
        SYNTAX       DisplayString
        MAX-ACCESS   read-only
        STATUS       current
        DESCRIPTION  "Memorandum (for display)."
        ::= { ipeSysInfoEntry 5 }

    ipeSysPrimaryIpAddress OBJECT-TYPE
        SYNTAX       IpAddress
        MAX-ACCESS   read-write
        STATUS       current
        DESCRIPTION  "Primary IP Address (for display and setting)."
        ::= { ipeSysInfoEntry 6 }

    ipeSysSubnetMask OBJECT-TYPE
        SYNTAX       IpAddress
        MAX-ACCESS   read-only
        STATUS       current
        DESCRIPTION  "Subnet mask (for display)."
        ::= { ipeSysInfoEntry 7 }

    ipeSysDefaultGateway OBJECT-TYPE
        SYNTAX       IpAddress
        MAX-ACCESS   read-only
        STATUS       current
        DESCRIPTION  "Default gateway (for display)."
        ::= { ipeSysInfoEntry 8 }

    ipeSysMacAddress OBJECT-TYPE
        SYNTAX       MacAddress
        MAX-ACCESS   read-only
        STATUS       current
        DESCRIPTION  "MAC address (for display)."
        ::= { ipeSysInfoEntry 9 }

    ipeSysMibVersion OBJECT-TYPE
        SYNTAX       DisplayString
        MAX-ACCESS   read-only
        STATUS       current
        DESCRIPTION  "MIB version."
        ::= { ipeSysInfoEntry 10 }

    ipeSysEquipmentType OBJECT-TYPE
        SYNTAX       Integer32
        MAX-ACCESS   read-only
        STATUS       current
        DESCRIPTION  "Equipment type."
        ::= { ipeSysInfoEntry 11 }

    ipeSysPmType OBJECT-TYPE
        SYNTAX       Integer32 (1..20)
        MAX-ACCESS   read-write
        STATUS       current
        DESCRIPTION  
            "Number of Branch.
            1=normalNE mode.
            1!=branchNE mode (2<= ipeSysPmType <= 20).
            7Branches(7), 8Branches(8) can not be set to this (iPASOLINK EX
            Advanced).
            The value Bridge1(11), Bridge2(12), Bridge3(13),
            Bridge4(14), Bridge5(15) Bridge6(16) are available (iPASOLINK EX
            Advanced)."
        ::= { ipeSysInfoEntry 12 }

    ipeSysPrimaryIpv6Address OBJECT-TYPE
        SYNTAX       Ipv6Address
        MAX-ACCESS   read-only
        STATUS       current
        DESCRIPTION  "Primary IPv6 Address (for display)."
        ::= { ipeSysInfoEntry 13 }

    ipeSysPrimaryIpv6AddressPrefixLength OBJECT-TYPE
        SYNTAX       InetAddressPrefixLength
        MAX-ACCESS   read-only
        STATUS       current
        DESCRIPTION  "Primary IPv6 Address Prefix Length (for display)."
        ::= { ipeSysInfoEntry 14 }

    ipeSysIpv6DefaultGateway OBJECT-TYPE
        SYNTAX       Ipv6Address
        MAX-ACCESS   read-only
        STATUS       current
        DESCRIPTION  "IPv6 Default gateway (for display)."
        ::= { ipeSysInfoEntry 15 }

    ipeSysIpv6DefaultGatewayIfIndex OBJECT-TYPE
        SYNTAX       INTEGER {
                         any(0),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-only
        STATUS       current
        DESCRIPTION  
            "The index value which uniquely identifies the local
            interface through which the default gateway is
            reachable."
        ::= { ipeSysInfoEntry 16 }

    ipeSysPrimaryIfIndex OBJECT-TYPE
        SYNTAX       INTEGER {
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-write
        STATUS       current
        DESCRIPTION  "Interface index of Prymary Ip Address."
        ::= { ipeSysInfoEntry 17 }

    ipeSysIpv4DropFilterEnable OBJECT-TYPE
        SYNTAX       EnableDisableValue
        MAX-ACCESS   read-write
        STATUS       current
        DESCRIPTION  
            "Enables or disables the drop filter for IPv4 packets on bridge
            and LCT interfaces.
            The disable(1) means to pass both incoming and outgoing IPv4
            packets on these interfaces.
            The enable(2) means to drop both incoming and outgoing IPv4
            packets on these interfaces.
            Note that ipeCfgBridgeIpStackMode: ipv4(1) and
            ipeSysIpv4DropFilterEnable: enable(2) cannot be set for the
            establishment of IPv4 communication."
        ::= { ipeSysInfoEntry 18 }

    ipeSysInventoryInfoTable OBJECT-TYPE
        SYNTAX       SEQUENCE OF IpeSysInventoryInfoEntry
        MAX-ACCESS   not-accessible
        STATUS       current
        DESCRIPTION  "Table of system basic information."
        ::= { ipeSystemGroup 2 }

    ipeSysInventoryInfoEntry OBJECT-TYPE
        SYNTAX       IpeSysInventoryInfoEntry
        MAX-ACCESS   not-accessible
        STATUS       current
        DESCRIPTION  "Entry of system basic information."
        INDEX        { ipeSysInventoryInfoIndex }
        ::= { ipeSysInventoryInfoTable 1 }

    IpeSysInventoryInfoEntry ::= SEQUENCE {
        ipeSysInventoryInfoIndex         Integer32,
        ipeSysInventoryInfoNEAddress     IpAddress,
        ipeSysInvSoftwareVersion         DisplayString,
        ipeSysInvSoftwareReleaseDate     DateAndTime,
        ipeSysInvDlSoftwareVersion       DisplayString,
        ipeSysInvOperationSide           Integer32,
        ipeSysInvStandbySoftwareVersion  DisplayString
    }

    ipeSysInventoryInfoIndex OBJECT-TYPE
        SYNTAX       Integer32 (1..1)
        MAX-ACCESS   not-accessible
        STATUS       current
        DESCRIPTION  "Index of table."
        ::= { ipeSysInventoryInfoEntry 1 }

    ipeSysInventoryInfoNEAddress OBJECT-TYPE
        SYNTAX       IpAddress
        MAX-ACCESS   not-accessible
        STATUS       current
        DESCRIPTION  ""
        ::= { ipeSysInventoryInfoEntry 2 }

    ipeSysInvSoftwareVersion OBJECT-TYPE
        SYNTAX       DisplayString
        MAX-ACCESS   read-only
        STATUS       current
        DESCRIPTION  "Software version."
        ::= { ipeSysInventoryInfoEntry 3 }

    ipeSysInvSoftwareReleaseDate OBJECT-TYPE
        SYNTAX       DateAndTime
        MAX-ACCESS   read-only
        STATUS       current
        DESCRIPTION  "Software update date and time."
        ::= { ipeSysInventoryInfoEntry 4 }

    ipeSysInvDlSoftwareVersion OBJECT-TYPE
        SYNTAX       DisplayString
        MAX-ACCESS   read-only
        STATUS       current
        DESCRIPTION  "Download control."
        ::= { ipeSysInventoryInfoEntry 5 }

    ipeSysInvOperationSide OBJECT-TYPE
        SYNTAX       Integer32
        MAX-ACCESS   read-only
        STATUS       current
        DESCRIPTION  "Active side information."
        ::= { ipeSysInventoryInfoEntry 6 }

    ipeSysInvStandbySoftwareVersion OBJECT-TYPE
        SYNTAX       DisplayString
        MAX-ACCESS   read-only
        STATUS       current
        DESCRIPTION  "Firmware version of inactive side."
        ::= { ipeSysInventoryInfoEntry 7 }

    ipeSysOperationGroup OBJECT IDENTIFIER
        ::= { ipeSystemGroup 3 }

    ipeSysOpTimeTable OBJECT-TYPE
        SYNTAX       SEQUENCE OF IpeSysOpTimeEntry
        MAX-ACCESS   not-accessible
        STATUS       current
        DESCRIPTION  "Table of date and time."
        ::= { ipeSysOperationGroup 1 }

    ipeSysOpTimeEntry OBJECT-TYPE
        SYNTAX       IpeSysOpTimeEntry
        MAX-ACCESS   not-accessible
        STATUS       current
        DESCRIPTION  "Entry of date and time."
        INDEX        { ipeSysOpTimeIndex }
        ::= { ipeSysOpTimeTable 1 }

    IpeSysOpTimeEntry ::= SEQUENCE {
        ipeSysOpTimeIndex      Integer32,
        ipeSysOpTimeNEAddress  IpAddress,
        ipeSysOpCurrentTime    DateAndTime,
        ipeSysOpStartTime      DateAndTime,
        ipeSysOpUpTime         Counter32
    }

    ipeSysOpTimeIndex OBJECT-TYPE
        SYNTAX       Integer32 (1..1)
        MAX-ACCESS   not-accessible
        STATUS       current
        DESCRIPTION  "Index of table."
        ::= { ipeSysOpTimeEntry 1 }

    ipeSysOpTimeNEAddress OBJECT-TYPE
        SYNTAX       IpAddress
        MAX-ACCESS   not-accessible
        STATUS       current
        DESCRIPTION  ""
        ::= { ipeSysOpTimeEntry 2 }

    ipeSysOpCurrentTime OBJECT-TYPE
        SYNTAX       DateAndTime
        MAX-ACCESS   read-write
        STATUS       current
        DESCRIPTION  "Current time."
        ::= { ipeSysOpTimeEntry 3 }

    ipeSysOpStartTime OBJECT-TYPE
        SYNTAX       DateAndTime
        MAX-ACCESS   read-only
        STATUS       current
        DESCRIPTION  "OS started time."
        ::= { ipeSysOpTimeEntry 4 }

    ipeSysOpUpTime OBJECT-TYPE
        SYNTAX       Counter32
        MAX-ACCESS   read-only
        STATUS       current
        DESCRIPTION  "Duration after OS started (second)."
        ::= { ipeSysOpTimeEntry 5 }

    ipeSysOpFileDownloadTable OBJECT-TYPE
        SYNTAX       SEQUENCE OF IpeSysOpFileDownloadEntry
        MAX-ACCESS   not-accessible
        STATUS       current
        DESCRIPTION  "Table of file download."
        ::= { ipeSysOperationGroup 2 }

    ipeSysOpFileDownloadEntry OBJECT-TYPE
        SYNTAX       IpeSysOpFileDownloadEntry
        MAX-ACCESS   not-accessible
        STATUS       current
        DESCRIPTION  "Entry of file download."
        INDEX        { ipeSysOpFileDownloadIndex }
        ::= { ipeSysOpFileDownloadTable 1 }

    IpeSysOpFileDownloadEntry ::= SEQUENCE {
        ipeSysOpFileDownloadIndex           Integer32,
        ipeSysOpFileDownloadNEAddress       IpAddress,
        ipeSysOpFileDownloadModule          INTEGER,
        ipeSysOpFileDownloadCpuResetDetail  INTEGER,
        ipeSysOpFileDownloadStatus          INTEGER,
        ipeSysOpFileDownloadCtrl            INTEGER,
        ipeSysOpFileDownloadProtocolType    INTEGER
    }

    ipeSysOpFileDownloadIndex OBJECT-TYPE
        SYNTAX       Integer32 (1..1)
        MAX-ACCESS   not-accessible
        STATUS       current
        DESCRIPTION  "Index of table."
        ::= { ipeSysOpFileDownloadEntry 1 }

    ipeSysOpFileDownloadNEAddress OBJECT-TYPE
        SYNTAX       IpAddress
        MAX-ACCESS   not-accessible
        STATUS       current
        DESCRIPTION  ""
        ::= { ipeSysOpFileDownloadEntry 2 }

    ipeSysOpFileDownloadModule OBJECT-TYPE
        SYNTAX       INTEGER {
                         invalid(0),
                         idu(1),
                         odu(2),
                         mdprm(3),
                         ipeFpga(5),
                         softkey(7),
                         cfgNet(8),
                         cfgEqu(9),
                         cfgUser(10),
                         https(11),
                         cliScript(15),
                         httpsKey(19),
                         httpsSignedCrt(21),
                         controller(23),
                         caCrt(24)
                     }
        MAX-ACCESS   read-only
        STATUS       current
        DESCRIPTION  
            "Program type. *'0:Invalidity' is used as an initial state.
            cliScripo(15) can not be set to this (iPASOLINK EX Advanced).
            The value controller(23) is available only for the iPASOLINK EX
            Advanced."
        ::= { ipeSysOpFileDownloadEntry 3 }

    ipeSysOpFileDownloadCpuResetDetail OBJECT-TYPE
        SYNTAX       INTEGER { invalid(0), revertReset(1), normReset(2) }
        MAX-ACCESS   read-write
        STATUS       current
        DESCRIPTION  
            "CPU reset control.
            
            0:Invalidity
            1:revert reset
            2:normal reset( without revert )
            
            *'0:Invalidity' is used as an initial state."
        ::= { ipeSysOpFileDownloadEntry 4 }

    ipeSysOpFileDownloadStatus OBJECT-TYPE
        SYNTAX       INTEGER {
                         invalid(0),
                         downloadCompleted(1),
                         downloadFailed(2),
                         downloadExecuting(3),
                         downloadSuspending(4)
                     }
        MAX-ACCESS   read-only
        STATUS       current
        DESCRIPTION  
            "Download result.
            
            0:Invalidity
            1:Completed
            2:Failed
            3:Executing
            4:Suspending
            
            *'0:Invalidity' is used as an initial state.
            
            *A change state is the following three kinds.
            1)When it operates normally: 
              (Start)->(3:Executing)->(1:Completed)
            2)When it cancels on the way:
              (Start)->(3:Executing)->(4:Suspending)-> (Completed)
            3)When unusual detection is carried out on the way:
              (Start)->(3:Executing)->(2:Failed)
            
            *The download start from excluding (3:Executing) is permitted.
            *The download start from (3:Executing) is not permitted.
            
            *Pertinent details: ipeSysOpFileDownloadCtrl"
        ::= { ipeSysOpFileDownloadEntry 5 }

    ipeSysOpFileDownloadCtrl OBJECT-TYPE
        SYNTAX       INTEGER {
                         invalid(0),
                         startDownload(1),
                         suspendDownload(2),
                         startUpload(3),
                         endUpload(4),
                         resetDownload(5)
                     }
        MAX-ACCESS   read-write
        STATUS       current
        DESCRIPTION  
            "Download control.
            
            0:Invalidity
            1:Download start
            2:Download suspend
            3:Upload start
            4:Upload end
            5:Download reset
            
            *'0:Invalidity' is used as an initial state.
            *'5:Download reset' terminates the FTP server(vsftpd) with the
            deletion processing in the type of the file for all download
            directory.
            
            *Pertinent details: ipeSysOpFileDownloadProtocolType
            *Pertinent details: ipeSysOpFileDownloadModule
            *Pertinent details: ipeSysOpFileDownloadStatus
            *Pertinent details: ipeFsUpdateFileStatus
            *Pertinent details: ipeFsUsbProcStatus
            
            [Race condition]
            *When ipeSysOpFileDownloadStatus is (3:Executing) or
            (4:Suspending), (1:Download start) is invalid.
            *When ipeSysOpFileDownloadStatus is (4:Suspending), (2:Download
            suspend) is invalid.
            *When ipeSysOpFileDownloadStatus is (0:Invalidity), (1:Download
            start) is valid, but do nothing.
            *When ipeFsUpdateFileStatusis(3:Executing), it is invalid. Other
            one is valid.
            *When ipeFsUsbProcStatus is (2:Normal:Process executing), it is
            invalid. Other one is valid.
            
            [Indispensable condition]
            *When it is  (1:Download start) or (3:Upload start), (4:Upload
            end),ipeSysOpFileDownloadProtocolType setup is indispensable."
        ::= { ipeSysOpFileDownloadEntry 6 }

    ipeSysOpFileDownloadProtocolType OBJECT-TYPE
        SYNTAX       INTEGER { invalid(0), ftp(1), sftp(2), http(3) }
        MAX-ACCESS   read-write
        STATUS       current
        DESCRIPTION  
            "Kind of protocol,
            
            *'0:Invalidity' is used as an initial state.
            
            *Pertinent details: ipeSysOpFileDownloadCtrl"
        ::= { ipeSysOpFileDownloadEntry 7 }

    ipeSysOpProgramPmonRmonClearTable OBJECT-TYPE
        SYNTAX       SEQUENCE OF IpeSysOpProgramPmonRmonClearEntry
        MAX-ACCESS   not-accessible
        STATUS       current
        DESCRIPTION  ""
        ::= { ipeSysOperationGroup 3 }

    ipeSysOpProgramPmonRmonClearEntry OBJECT-TYPE
        SYNTAX       IpeSysOpProgramPmonRmonClearEntry
        MAX-ACCESS   not-accessible
        STATUS       current
        DESCRIPTION  ""
        INDEX        { ipeSysOpProgramPmonRmonClearIndex }
        ::= { ipeSysOpProgramPmonRmonClearTable 1 }

    IpeSysOpProgramPmonRmonClearEntry ::= SEQUENCE {
        ipeSysOpProgramPmonRmonClearIndex      Integer32,
        ipeSysOpProgramPmonRmonClearNEAddress  IpAddress,
        ipeSysOpProgramPmonRmonClear           Integer32,
        ipeSysOpProgramPmonRmonClearResult     INTEGER
    }

    ipeSysOpProgramPmonRmonClearIndex OBJECT-TYPE
        SYNTAX       Integer32 (1..1)
        MAX-ACCESS   not-accessible
        STATUS       current
        DESCRIPTION  ""
        ::= { ipeSysOpProgramPmonRmonClearEntry 1 }

    ipeSysOpProgramPmonRmonClearNEAddress OBJECT-TYPE
        SYNTAX       IpAddress
        MAX-ACCESS   not-accessible
        STATUS       current
        DESCRIPTION  ""
        ::= { ipeSysOpProgramPmonRmonClearEntry 2 }

    ipeSysOpProgramPmonRmonClear OBJECT-TYPE
        SYNTAX       Integer32
        MAX-ACCESS   read-write
        STATUS       current
        DESCRIPTION  
            "PMON data clear control
            0:FIXED VALUE 1:REQUEST"
        ::= { ipeSysOpProgramPmonRmonClearEntry 3 }

    ipeSysOpProgramPmonRmonClearResult OBJECT-TYPE
        SYNTAX       INTEGER { invalid(0), completed(1), failed(2), executing(3) }
        MAX-ACCESS   read-only
        STATUS       current
        DESCRIPTION  
            "PMON data clear control response
            1:COMPLETED
            2:FAILED
            3:EXECUTING"
        ::= { ipeSysOpProgramPmonRmonClearEntry 4 }

    ipeFileSystemGroup OBJECT IDENTIFIER
        ::= { system5 2 }

    ipeFsFileInfoTable OBJECT-TYPE
        SYNTAX       SEQUENCE OF IpeFsFileInfoEntry
        MAX-ACCESS   not-accessible
        STATUS       current
        DESCRIPTION  "Table of file information."
        ::= { ipeFileSystemGroup 1 }

    ipeFsFileInfoEntry OBJECT-TYPE
        SYNTAX       IpeFsFileInfoEntry
        MAX-ACCESS   not-accessible
        STATUS       current
        DESCRIPTION  "Entry of file information."
        INDEX        { ipeFsFileInfoIndex }
        ::= { ipeFsFileInfoTable 1 }

    IpeFsFileInfoEntry ::= SEQUENCE {
        ipeFsFileInfoIndex            Integer32,
        ipeFsFileInfoNEAddress        IpAddress,
        ipeFsFileListType             INTEGER,
        ipeFsFileListCurrent          DisplayString,
        ipeFsFileListTemp             DisplayString,
        ipeFsUpdateFileDetail         DisplayString,
        ipeFsUpdateFileStatus         INTEGER,
        ipeFsUpdateFileStatusDetail   OCTET STRING,
        ipeFsUpdateFileProgressBase   Integer32,
        ipeFsUpdateFileProgress       Integer32,
        ipeFsUpdateFileUpdateList     DisplayString,
        ipeFsUpdateFileConfigPartial  OCTET STRING
    }

    ipeFsFileInfoIndex OBJECT-TYPE
        SYNTAX       Integer32 (1..1)
        MAX-ACCESS   not-accessible
        STATUS       current
        DESCRIPTION  "Index of Table."
        ::= { ipeFsFileInfoEntry 1 }

    ipeFsFileInfoNEAddress OBJECT-TYPE
        SYNTAX       IpAddress
        MAX-ACCESS   not-accessible
        STATUS       current
        DESCRIPTION  ""
        ::= { ipeFsFileInfoEntry 2 }

    ipeFsFileListType OBJECT-TYPE
        SYNTAX       INTEGER {
                         invalid(0),
                         idu(1),
                         odu(2),
                         mdprm(3),
                         raFpga(4),
                         ipeFpga(5),
                         softkey(7),
                         cfgNet(8),
                         cfgEqu(9),
                         cfgUser(10),
                         https(11),
                         pmon(12),
                         rmon(13),
                         log(14),
                         inventory(15),
                         mac(16),
                         all(17),
                         cardFw(18),
                         httpsKey(19),
                         httpsCsr(20),
                         httpsSignedCrt(21),
                         controller(23),
                         caCrt(24)
                     }
        MAX-ACCESS   read-write
        STATUS       current
        DESCRIPTION  
            "Type for acquisition
            
            0:Invalidity
            1: IDU
            2: ODU
            3: MODEM Parameter
            4: FPGA(Other slot)
            5: FPGA(Ctrl)
            6: MSE
            7: Software Key License
            8: Network Config
            9: Equipment Config
            10: User Config
            11: Server Certificate for HTTPS/HTTPS certificate issue request
            12: PMON data
            13: RMON data
            14: Command/event/alarm LOG
            15: Device Inventory file
            16: MAC learning entry
            17: all(All types)
            18: Card Firmware
            19: Private key for SSL Server Certificate
            20: CSR (Certificate Signing Request) for SSL Server Certificate
            21: CA (Certification Authority) signed certificate for SSL
            Server Certificate
            22: Modem Controller(valid for MODEM-AV)
            24: CA (Certification Authority) certificate
            50: SD
            51: TRP
            52: TR Interface
            
            *'0:Invalidity' is used as an initial state.
            *'8: Network Config' can not be set to this (iPASOLINK EX
            Advanced).
            *'9: Equipment Config' is used for Equipment and Network
            Configuration only for the iPASOLINK EX Advanced.
            
            *Pertinent details: ipeFsFileListCurrent
            *Pertinent details: ipeFsFileListTemp"
        ::= { ipeFsFileInfoEntry 3 }

    ipeFsFileListCurrent OBJECT-TYPE
        SYNTAX       DisplayString
        MAX-ACCESS   read-only
        STATUS       current
        DESCRIPTION  
            "Current file list (Flash-ROM).
            
            The list of the type set to ipeFsFileListType is acquired. 
            
            Form of file list:
            
            It's 1 item by  'file name (It included in a path),file
            size,CRC'.
            Each item is divided at space.
            
            *CRC is fixed '0'. 
            
            Ex) FilePath1/FileName1,size,CRC FilePath2/FileName2,size,CRC...
            
            [Indispensable condition]
            *ipeFsFileListType setup is indispensable."
        ::= { ipeFsFileInfoEntry 4 }

    ipeFsFileListTemp OBJECT-TYPE
        SYNTAX       DisplayString
        MAX-ACCESS   read-only
        STATUS       current
        DESCRIPTION  
            "Temporary file list (DRAM).
            
            The list of the type set to ipeFsFileListType is acquired. 
            
            Form of file list:
            
            It's 1 item by 'file name (It isn't included in a pass),file
            size,CRC'.
            Each item is divided at space.
            
            *CRC is fixed '0'. 
            
            Ex) Filename1,size,CRC Filename2,size,CRC...
            
            [Indispensable condition]
            *ipeFsFileListType setup is indispensable."
        ::= { ipeFsFileInfoEntry 5 }

    ipeFsUpdateFileDetail OBJECT-TYPE
        SYNTAX       DisplayString
        MAX-ACCESS   read-write
        STATUS       current
        DESCRIPTION  
            "File update control.
            
            Thing to specify object file after it downloads it by
            'ipeSysOpFileDownloadCtrl','ipeFsUsbCommand' and to demand file
            update.
            
            
            *Pertinent details: ipeSysOpFileDownloadModule
            *Pertinent details: ipeFsUpdateFileUpdateList
            *Pertinent details: ipeSysOpFileDownloadStatus
            *Pertinent details: ipeFsUpdateFileStatus
            *Pertinent details: ipeFsUsbProcStatus
            
            [Race condition]
            *When ipeSysOpFileDownloadStatus is (3:Executing) or
            (4:Suspending), it is invalid.
            *When ipeFsUpdateFileStatusis(3:Executing), it is invalid. 
            *When ipeFsUsbProcStatus is (2:Normal :Process executing), it is
            invalid.
            
            [Indispensable condition]
            *When ipeSysOpFileDownloadModule is 'odu(2)', 'mdprm(3)', or
            'raFpga(4)', ipeFsUpdateFileUpdateList setup is indispensable."
        ::= { ipeFsFileInfoEntry 6 }

    ipeFsUpdateFileStatus OBJECT-TYPE
        SYNTAX       INTEGER {
                         invalid(0),
                         success(1),
                         failure(2),
                         executing(3),
                         checking(4),
                         successWithoutRestrictedUser(5)
                     }
        MAX-ACCESS   read-only
        STATUS       current
        DESCRIPTION  
            "Update result.
              0:Invalidity
              1:Success
              2:Failed
              3:Executing
              4:Checking
              5:Success but some restricted UserName(s) are ignored
            
            *'0:Invalidity' is used as an initial state.
            
            *The slot result of the correspondence is set to
            'IpeFsUpdateFileStatusDetail',
              and processing is continued when failing in the two or more
            slot update.
            
            *Pertinent details: ipeFsUpdateFileDetail
            *Pertinent details: ipeFsUpdateFileStatusDetail"
        ::= { ipeFsFileInfoEntry 7 }

    ipeFsUpdateFileStatusDetail OBJECT-TYPE
        SYNTAX       OCTET STRING (SIZE(42..42))
        MAX-ACCESS   read-only
        STATUS       current
        DESCRIPTION  
            "Update result is detailed. 
            
            OCT: Update result of each slot
                  1: Completed
                  2: Failed
            
            The slot for which the current state is used becomes the
            following.
            
            OCT[0] : MainBoard(iPASO200)   or SLOT0
            OCT[1] : MODEM1(iPASO200)      or SLOT1
            OCT[2] : MODEM2(iPASO200)      or SLOT2
            OCT[3] : Option Card(iPASO200) or SLOT3
              :
            OCT[33]: ODU1
            OCT[34]: ODU2
            OCT[35]: ODU3
              :
            
            *Pertinent details: ipeSysOpFileDownloadCtrl
            *Pertinent details: ipeFsUpdateFileDetail
            *Pertinent details: ipeFsUsbCommand"
        ::= { ipeFsFileInfoEntry 8 }

    ipeFsUpdateFileProgressBase OBJECT-TYPE
        SYNTAX       Integer32
        MAX-ACCESS   read-only
        STATUS       current
        DESCRIPTION  
            "Progress of update (denominator).
            
            *Pertinent details: ipeSysOpFileDownloadModule
            *Pertinent details: ipeFsUpdateFileStatus"
        ::= { ipeFsFileInfoEntry 9 }

    ipeFsUpdateFileProgress OBJECT-TYPE
        SYNTAX       Integer32
        MAX-ACCESS   read-only
        STATUS       current
        DESCRIPTION  
            "Progress of update (molecule).
            
            *Pertinent details: ipeSysOpFileDownloadModule
            *Pertinent details: ipeFsUpdateFileStatus"
        ::= { ipeFsFileInfoEntry 10 }

    ipeFsUpdateFileUpdateList OBJECT-TYPE
        SYNTAX       DisplayString
        MAX-ACCESS   read-write
        STATUS       current
        DESCRIPTION  
            "Definition of update slot number.
            
            Form of file list:
            When downloading it to ODU/FPGA/MDPRM, the forwarding site slot
            number is enumerated by a comma end.
            
            Ex) 0,5,1,6,10...
              The slot number of relating MODEM and fpga must set the slot
            number of
              Option Card to odu and mdprm according to inventory
            information.
            
            The slot number to which the current state can be set becomes the
            following.
            
            iPASO200             iPASO400,1000
            0 : MainBoard     or SLOT0
            1 : MODEM1        or SLOT1
            2 : MODEM2        or SLOT2
            3 : Option Card   or SLOT3
                  :
            33: ODU1
            34: ODU2
            35: ODU3
                  :
            
            *Pertinent details: ipeFsUpdateFileDetail"
        ::= { ipeFsFileInfoEntry 11 }

    ipeFsUpdateFileConfigPartial OBJECT-TYPE
        SYNTAX       OCTET STRING (SIZE(4..4))
        MAX-ACCESS   read-write
        STATUS       obsolete
        DESCRIPTION  
            "Specify Equipment Configuration Partial Download pattern.
            If this object is set with ipeFsUpdateFileDetail, the system will
            perform the partial download, otherwise the system will perform
            the normal download. And Partial Download is performed only when
            Equipment Configuration Dowload.
            
            SYNTAX is 32bit string. The definition of each bit is shown
            below.
            
            - bit1-4: specify download mode.
             0001 : normal mode
             other value : reserved (system rejects the request)
            - bit5-32: specify the equipment config part. Setting 1 to each
            bit means corresponding config download is activated.
             Bit5 : Equipment Configuration (must set when the normal mode)
             Bit6 : Radio Configuration
             Bit7 : Radio Configuration w/o Radio Frequency
                    Bit6 and Bit7 cannot be set to 1 simultaneously.
             Bit8 : E1/STM1 Mapping (must set when Bit6 or Bit7 is activated)
             Bit9 : MODEM Function setting
             Bit10: ETH Function setting
             Bit11: E1/STM1/Cross Connect Setting
             Bit12: PWE Setting
             Bit13: Equipment Clock/Synchronization Setting
             Bit14: Relay-Alarm Mapping
             Bit15: V11/OW Setting
             Bit16: Alarm/AIS Setting
             Bit17: PMON/RMON Setting
             Bit18: AUX Setting
            
             other: reserved (don't care)
            
            Example)
             the pattern of downloading the equipment configuration, radio
            configuration, E1/STM1 mapping, ETH Function Setting on normal
            mode.
              ipeFsUpdateFileConfigPartial = 
                      '00011101010000000000000000000000'"
        ::= { ipeFsFileInfoEntry 12 }

    ipeFsUsbInfoTable OBJECT-TYPE
        SYNTAX       SEQUENCE OF IpeFsUsbInfoEntry
        MAX-ACCESS   not-accessible
        STATUS       current
        DESCRIPTION  "Table of USB memory information."
        ::= { ipeFileSystemGroup 2 }

    ipeFsUsbInfoEntry OBJECT-TYPE
        SYNTAX       IpeFsUsbInfoEntry
        MAX-ACCESS   not-accessible
        STATUS       current
        DESCRIPTION  "Entry of USB mamory information."
        INDEX        { ipeFsUsbInfoIndex }
        ::= { ipeFsUsbInfoTable 1 }

    IpeFsUsbInfoEntry ::= SEQUENCE {
        ipeFsUsbInfoIndex      Integer32,
        ipeFsUsbInfoNEAddress  IpAddress,
        ipeFsUsbCommand        DisplayString,
        ipeFsUsbProcStatus     INTEGER,
        ipeFsUsbList           DisplayString,
        ipeFsUsbConnectStatus  INTEGER
    }

    ipeFsUsbInfoIndex OBJECT-TYPE
        SYNTAX       Integer32 (1..1)
        MAX-ACCESS   not-accessible
        STATUS       current
        DESCRIPTION  "Index of Table."
        ::= { ipeFsUsbInfoEntry 1 }

    ipeFsUsbInfoNEAddress OBJECT-TYPE
        SYNTAX       IpAddress
        MAX-ACCESS   not-accessible
        STATUS       current
        DESCRIPTION  ""
        ::= { ipeFsUsbInfoEntry 2 }

    ipeFsUsbCommand OBJECT-TYPE
        SYNTAX       DisplayString
        MAX-ACCESS   read-write
        STATUS       current
        DESCRIPTION  
            "USB control mode/USB file path/Program type specification.
            
            [Mode],[Arg1],[Type]
              Mode:USB control mode
                0:DL, 1:UL
              Arg1:object file path -1 (original file path (path from a
            chroot subordinate) When DL: Inside of USB, When UL: Inside of
            IPE)
                  Case of DL: Ex.) idu/iPASOLINK200-idufw-v1.00.XX.bin
                  Case of UL: Ex.) export/config/iPASOLINK-network.cfg
              Type:Program type
                  The program type set to  'ipeSysOpFileDownloadModule' is
            specified.
                  *The unsetting is allowed for an arbitrary, set item. 
            
                 0: Invalid
                 1: IDU F/W
                 2: ODU F/W
                 3: MODEM Parameter
                 4: FPGA(Option Card)
                 5: FPGA(MainBoard)
                 6: MSE Card F/W
                 7: Software License Key
                 8: Network Config
                 9: Equipment Config
                10: User Config
                11: HTTPS Server Certificate
            
            *The object file name allows only alphanumeric character '0-9',
            'a-z', 'A-Z' of ASCII code, and sign '-_.+'.
            
            *Pertinent details: ipeSysOpFileDownloadModule
            *Pertinent details: ipeSysOpFileDownloadStatus
            *Pertinent details: ipeFsUpdateFileStatus
            *Pertinent details: ipeFsUsbProcStatus
            
            [Race condition]
            *When ipeSysOpFileDownloadStatus is (3:Executing) or
            (4:Suspending), (0:DL) is invalid.
            *When ipeFsUpdateFileStatusis (3:Executing),  (0:DL) is invalid.
            *When ipeFsUsbProcStatus is (2:Normal :Process executing), 
            (0:DL) is invalid."
        ::= { ipeFsUsbInfoEntry 3 }

    ipeFsUsbProcStatus OBJECT-TYPE
        SYNTAX       INTEGER {
                         invalid(0),
                         completed(1),
                         executing(2),
                         diskFullError(98),
                         noSuchFileError(99),
                         unKnownFileError(101),
                         notInsertError(102),
                         accessError(103),
                         otherError(127)
                     }
        MAX-ACCESS   read-only
        STATUS       current
        DESCRIPTION  
            "Status of USB memory control result.
            
            The classification of a setting value and the meaning are as
            follows.
              0:Invalidity
              1:NORMAL:Normal end
              2:NORMAL:Executing
             98:ERROR:The lack of free space on disk or media
             99:ERROR:File/directory not found
            101:ERROR:The kind of designated files,the size, contents, etc.
            are unjust
            102:ERROR:Media aren't inserted
            103:ERROR:Media access error (ex:unjust format)
            127:ERROR:Undefined error (other errors)
            When having a control instruction, it's made '2:Executing'.
            
            *'0:Invalidity' is used as an initial state.
            
            *Pertinent details: ipeFsUsbCommand"
        ::= { ipeFsUsbInfoEntry 4 }

    ipeFsUsbList OBJECT-TYPE
        SYNTAX       DisplayString
        MAX-ACCESS   read-only
        STATUS       current
        DESCRIPTION  
            "File list format.
            
            Form of file list:
            
            It's 1 item by 'file name (path from a chroot subordinate),file
            size,CRC'.
            Each item is divided at space.
            
            *CRC is fixed '0'. 
            
            Ex) FilePath1/FileName1,size,CRC FilePath2/FileName2,size,CRC..."
        ::= { ipeFsUsbInfoEntry 5 }

    ipeFsUsbConnectStatus OBJECT-TYPE
        SYNTAX       INTEGER { usbConnect(1), usbNoConnect(2) }
        MAX-ACCESS   read-only
        STATUS       current
        DESCRIPTION  
            "Status of connection USB memory.
            
            1:Connect
            2:Not connect"
        ::= { ipeFsUsbInfoEntry 6 }

    ipeConfigurationGroup OBJECT IDENTIFIER
        ::= { system5 3 }

    ipeCfgSystemTable OBJECT-TYPE
        SYNTAX       SEQUENCE OF IpeCfgSystemEntry
        MAX-ACCESS   not-accessible
        STATUS       current
        DESCRIPTION  "Table of System Item Information."
        ::= { ipeConfigurationGroup 1 }

    ipeCfgSystemEntry OBJECT-TYPE
        SYNTAX       IpeCfgSystemEntry
        MAX-ACCESS   not-accessible
        STATUS       current
        DESCRIPTION  "Entry of System Item Information."
        INDEX        { ipeCfgSystemIndex }
        ::= { ipeCfgSystemTable 1 }

    IpeCfgSystemEntry ::= SEQUENCE {
        ipeCfgSystemIndex      Integer32,
        ipeCfgSystemNEAddress  IpAddress,
        ipeCfgNeName           DisplayString,
        ipeCfgAreaName         DisplayString,
        ipeCfgMemo             DisplayString
    }

    ipeCfgSystemIndex OBJECT-TYPE
        SYNTAX       Integer32 (1..1)
        MAX-ACCESS   not-accessible
        STATUS       current
        DESCRIPTION  "Index of table."
        ::= { ipeCfgSystemEntry 1 }

    ipeCfgSystemNEAddress OBJECT-TYPE
        SYNTAX       IpAddress
        MAX-ACCESS   not-accessible
        STATUS       current
        DESCRIPTION  ""
        ::= { ipeCfgSystemEntry 2 }

    ipeCfgNeName OBJECT-TYPE
        SYNTAX       DisplayString
        MAX-ACCESS   read-write
        STATUS       current
        DESCRIPTION  
            "PASOLINK unit name. White space characters are not allowed for
            head or tail of characters."
        ::= { ipeCfgSystemEntry 3 }

    ipeCfgAreaName OBJECT-TYPE
        SYNTAX       DisplayString
        MAX-ACCESS   read-write
        STATUS       current
        DESCRIPTION  
            "Area name. White space characters are not allowed for head or
            tail of characters."
        ::= { ipeCfgSystemEntry 4 }

    ipeCfgMemo OBJECT-TYPE
        SYNTAX       DisplayString
        MAX-ACCESS   read-write
        STATUS       current
        DESCRIPTION  
            "Memorandum. White space characters are not allowed for head or
            tail of characters."
        ::= { ipeCfgSystemEntry 5 }

    ipeCfgOemTable OBJECT-TYPE
        SYNTAX       SEQUENCE OF IpeCfgOemEntry
        MAX-ACCESS   not-accessible
        STATUS       current
        DESCRIPTION  "Table of Equipment Item Information."
        ::= { ipeConfigurationGroup 2 }

    ipeCfgOemEntry OBJECT-TYPE
        SYNTAX       IpeCfgOemEntry
        MAX-ACCESS   not-accessible
        STATUS       current
        DESCRIPTION  "Entry of Equipment Item Information."
        INDEX        { ipeCfgOemIndex }
        ::= { ipeCfgOemTable 1 }

    IpeCfgOemEntry ::= SEQUENCE {
        ipeCfgOemIndex        Integer32,
        ipeCfgOemNEAddress    IpAddress,
        ipeCfgOemSysDescr     DisplayString,
        ipeCfgOemSysContact   DisplayString,
        ipeCfgOemSysName      DisplayString,
        ipeCfgOemSysLocation  DisplayString
    }

    ipeCfgOemIndex OBJECT-TYPE
        SYNTAX       Integer32 (1..1)
        MAX-ACCESS   not-accessible
        STATUS       current
        DESCRIPTION  "Index of table."
        ::= { ipeCfgOemEntry 1 }

    ipeCfgOemNEAddress OBJECT-TYPE
        SYNTAX       IpAddress
        MAX-ACCESS   not-accessible
        STATUS       current
        DESCRIPTION  ""
        ::= { ipeCfgOemEntry 2 }

    ipeCfgOemSysDescr OBJECT-TYPE
        SYNTAX       DisplayString
        MAX-ACCESS   read-write
        STATUS       current
        DESCRIPTION  
            "System Description.
            The space of the begininng and end dose not permit it."
        ::= { ipeCfgOemEntry 3 }

    ipeCfgOemSysContact OBJECT-TYPE
        SYNTAX       DisplayString
        MAX-ACCESS   read-write
        STATUS       current
        DESCRIPTION  
            "System contact.
            The space of the begininng and end dose not permit it."
        ::= { ipeCfgOemEntry 4 }

    ipeCfgOemSysName OBJECT-TYPE
        SYNTAX       DisplayString
        MAX-ACCESS   read-write
        STATUS       current
        DESCRIPTION  
            "System name.
            The space of the begininng and end dose not permit it."
        ::= { ipeCfgOemEntry 5 }

    ipeCfgOemSysLocation OBJECT-TYPE
        SYNTAX       DisplayString
        MAX-ACCESS   read-write
        STATUS       current
        DESCRIPTION  
            "System location.
            The space of the begininng and end dose not permit it."
        ::= { ipeCfgOemEntry 6 }

    ipeCfgNtp OBJECT IDENTIFIER
        ::= { ipeConfigurationGroup 4 }

    ipeCfgNtpServiceTable OBJECT-TYPE
        SYNTAX       SEQUENCE OF IpeCfgNtpServiceEntry
        MAX-ACCESS   not-accessible
        STATUS       current
        DESCRIPTION  "Table of NTP configuration information."
        ::= { ipeCfgNtp 1 }

    ipeCfgNtpServiceEntry OBJECT-TYPE
        SYNTAX       IpeCfgNtpServiceEntry
        MAX-ACCESS   not-accessible
        STATUS       current
        DESCRIPTION  "Entry of NTP configuration information."
        INDEX        { ipeCfgNtpServiceIndex }
        ::= { ipeCfgNtpServiceTable 1 }

    IpeCfgNtpServiceEntry ::= SEQUENCE {
        ipeCfgNtpServiceIndex                 Integer32,
        ipeCfgNtpServiceNEAddress             IpAddress,
        ipeCfgNtpServiceEnable                INTEGER,
        ipeCfgNtpServerMode                   INTEGER,
        ipeCfgNtpClientMode                   INTEGER,
        ipeCfgNtpServerStratum                Integer32,
        ipeCfgNtpServerMulticastPort          Integer32,
        ipeCfgNtpServerMulticastIntervalTime  Integer32,
        ipeCfgNtpAuthenticationEnable         EnableDisableValue,
        ipeCfgNtpServerMulticastAuthKeyIndex  IpeNtpKeyAdminIndexOrZero
    }

    ipeCfgNtpServiceIndex OBJECT-TYPE
        SYNTAX       Integer32 (1..1)
        MAX-ACCESS   not-accessible
        STATUS       current
        DESCRIPTION  "Index of table."
        ::= { ipeCfgNtpServiceEntry 1 }

    ipeCfgNtpServiceNEAddress OBJECT-TYPE
        SYNTAX       IpAddress
        MAX-ACCESS   not-accessible
        STATUS       current
        DESCRIPTION  ""
        ::= { ipeCfgNtpServiceEntry 2 }

    ipeCfgNtpServiceEnable OBJECT-TYPE
        SYNTAX       INTEGER { invalid(0), disabled(1), enabled(2) }
        MAX-ACCESS   read-write
        STATUS       current
        DESCRIPTION  "NTP control enable."
        ::= { ipeCfgNtpServiceEntry 3 }

    ipeCfgNtpServerMode OBJECT-TYPE
        SYNTAX       INTEGER { invalid(0), unicast(1), multicast(2), disabled(3) }
        MAX-ACCESS   read-write
        STATUS       current
        DESCRIPTION  "NTP server mode."
        ::= { ipeCfgNtpServiceEntry 4 }

    ipeCfgNtpClientMode OBJECT-TYPE
        SYNTAX       INTEGER { invalid(0), unicast(1), multicast(2), disabled(3) }
        MAX-ACCESS   read-write
        STATUS       current
        DESCRIPTION  "NTP client mode."
        ::= { ipeCfgNtpServiceEntry 5 }

    ipeCfgNtpServerStratum OBJECT-TYPE
        SYNTAX       Integer32 (2..15)
        MAX-ACCESS   read-write
        STATUS       current
        DESCRIPTION  "NTP Stratum."
        ::= { ipeCfgNtpServiceEntry 6 }

    ipeCfgNtpServerMulticastPort OBJECT-TYPE
        SYNTAX       Integer32
        MAX-ACCESS   read-write
        STATUS       current
        DESCRIPTION  
            "NTP server multicast port.
            Bridge7(17), Bridge8(18) can not be set to this (iPASOLINK EX
            Advanced).
            The value Bridge1(11), Bridge2(12), Bridge3(13),
            Bridge4(14), Bridge5(15) Bridge6(16) are available (iPASOLINK EX
            Advanced)."
        ::= { ipeCfgNtpServiceEntry 7 }

    ipeCfgNtpServerMulticastIntervalTime OBJECT-TYPE
        SYNTAX       Integer32 (4..17)
        MAX-ACCESS   read-write
        STATUS       current
        DESCRIPTION  "Value of NTP multicast polling time."
        ::= { ipeCfgNtpServiceEntry 8 }

    ipeCfgNtpAuthenticationEnable OBJECT-TYPE
        SYNTAX       EnableDisableValue
        MAX-ACCESS   read-write
        STATUS       current
        DESCRIPTION  "Enabling NTP authentication."
        ::= { ipeCfgNtpServiceEntry 9 }

    ipeCfgNtpServerMulticastAuthKeyIndex OBJECT-TYPE
        SYNTAX       IpeNtpKeyAdminIndexOrZero
        MAX-ACCESS   read-write
        STATUS       current
        DESCRIPTION  
            "Configuring Authentication Key Index.
            This value is available only when the system is running on the
            NTP multicast server mode."
        ::= { ipeCfgNtpServiceEntry 10 }

    ipeCfgNtpServerTable OBJECT-TYPE
        SYNTAX       SEQUENCE OF IpeCfgNtpServerEntry
        MAX-ACCESS   not-accessible
        STATUS       current
        DESCRIPTION  "Table of NTP server information."
        ::= { ipeCfgNtp 2 }

    ipeCfgNtpServerEntry OBJECT-TYPE
        SYNTAX       IpeCfgNtpServerEntry
        MAX-ACCESS   not-accessible
        STATUS       current
        DESCRIPTION  "Entry of NTP server information."
        INDEX        { ipeCfgNtpServerIndex }
        ::= { ipeCfgNtpServerTable 1 }

    IpeCfgNtpServerEntry ::= SEQUENCE {
        ipeCfgNtpServerIndex         Integer32,
        ipeCfgNtpServerNEAddress     IpAddress,
        ipeCfgNtpServerAddress       IpAddress,
        ipeCfgNtpVersion             Integer32,
        ipeCfgNtpPollTime            Integer32,
        ipeCfgNtpServerAuthKeyIndex  IpeNtpKeyAdminIndexOrZero,
        ipeCfgNtpServerV6Address     Ipv6Address,
        ipeCfgNtpServerAddressType   INTEGER
    }

    ipeCfgNtpServerIndex OBJECT-TYPE
        SYNTAX       Integer32 (1..4)
        MAX-ACCESS   not-accessible
        STATUS       current
        DESCRIPTION  "Index of table."
        ::= { ipeCfgNtpServerEntry 1 }

    ipeCfgNtpServerNEAddress OBJECT-TYPE
        SYNTAX       IpAddress
        MAX-ACCESS   not-accessible
        STATUS       current
        DESCRIPTION  ""
        ::= { ipeCfgNtpServerEntry 2 }

    ipeCfgNtpServerAddress OBJECT-TYPE
        SYNTAX       IpAddress
        MAX-ACCESS   read-write
        STATUS       current
        DESCRIPTION  "IP Address of NTP server."
        ::= { ipeCfgNtpServerEntry 3 }

    ipeCfgNtpVersion OBJECT-TYPE
        SYNTAX       Integer32 (3..4)
        MAX-ACCESS   read-write
        STATUS       current
        DESCRIPTION  "Version of supported NTP message."
        ::= { ipeCfgNtpServerEntry 4 }

    ipeCfgNtpPollTime OBJECT-TYPE
        SYNTAX       Integer32 (4..17)
        MAX-ACCESS   read-write
        STATUS       current
        DESCRIPTION  
            "NTP Polling Time, in seconds as a power of two.
            For instance, a value of six indicates a interval of 64 seconds.
            
            Note) The value less than 6 is rejected by the agent because of
            the system recommendation.
             iPASOLINK 200/400/1000 series : R3.5 or later.
             iPASOLINK AOR : R1.0 or later."
        ::= { ipeCfgNtpServerEntry 5 }

    ipeCfgNtpServerAuthKeyIndex OBJECT-TYPE
        SYNTAX       IpeNtpKeyAdminIndexOrZero
        MAX-ACCESS   read-write
        STATUS       current
        DESCRIPTION  "Configuring Authentication Key Index per NTP server."
        ::= { ipeCfgNtpServerEntry 6 }

    ipeCfgNtpServerV6Address OBJECT-TYPE
        SYNTAX       Ipv6Address
        MAX-ACCESS   read-write
        STATUS       current
        DESCRIPTION  
            "IPv6 Address of NTP Server. 
            
            When this object is configured, the NTP Client will run 
            over IPv6 and the ipeCfgNtpServerAddress will be 
            unconfigured (reset to 0.0.0.0).
            
            When configuring ipeCfgNtpServerAddress, the NTP Client 
            will run over IPv4 and this object will be unconfigured
            (reset to ::).
            
            The following are not valid addresses:
              ::1/128 IPv6 Loopback
              FE80::/10 Link local
              FF00::/8 IPv6 Multicasts"
        ::= { ipeCfgNtpServerEntry 7 }

    ipeCfgNtpServerAddressType OBJECT-TYPE
        SYNTAX       INTEGER { invalid(0), ipv4(1), ipv6(2) }
        MAX-ACCESS   read-write
        STATUS       current
        DESCRIPTION  
            "Indicate IP address type of this server.
            
            ipv4 : server has IPv4 address.
            ipv6 : server has IPv6 address."
        ::= { ipeCfgNtpServerEntry 8 }

    ipeCfgNtpAuthenticationKeyTable OBJECT-TYPE
        SYNTAX       SEQUENCE OF IpeCfgNtpAuthenticationKeyEntry
        MAX-ACCESS   not-accessible
        STATUS       current
        DESCRIPTION  "This table contains the NTP authentication keys."
        ::= { ipeCfgNtp 3 }

    ipeCfgNtpAuthenticationKeyEntry OBJECT-TYPE
        SYNTAX       IpeCfgNtpAuthenticationKeyEntry
        MAX-ACCESS   not-accessible
        STATUS       current
        DESCRIPTION  ""
        INDEX        { ipeCfgNtpAuthenticationKeyIndex }
        ::= { ipeCfgNtpAuthenticationKeyTable 1 }

    IpeCfgNtpAuthenticationKeyEntry ::= SEQUENCE {
        ipeCfgNtpAuthenticationKeyIndex    IpeNtpKeyAdminIndex,
        ipeCfgNtpAuthenticationNEAddress   IpAddress,
        ipeCfgNtpAuthenticationAlgorithm   INTEGER,
        ipeCfgNtpAuthenticationKey         DisplayString,
        ipeCfgNtpAuthenticationKeyId       Unsigned32,
        ipeCfgNtpAuthenticationKeyTrusted  OffOnValue,
        ipeCfgNtpAuthKeyRowStatus          RowStatus
    }

    ipeCfgNtpAuthenticationKeyIndex OBJECT-TYPE
        SYNTAX       IpeNtpKeyAdminIndex
        MAX-ACCESS   not-accessible
        STATUS       current
        DESCRIPTION  
            "Administrative index of this table.
            The value is different from ipeCfgNtpAuthenticationKeyId."
        ::= { ipeCfgNtpAuthenticationKeyEntry 1 }

    ipeCfgNtpAuthenticationNEAddress OBJECT-TYPE
        SYNTAX       IpAddress
        MAX-ACCESS   not-accessible
        STATUS       current
        DESCRIPTION  "reserved."
        ::= { ipeCfgNtpAuthenticationKeyEntry 2 }

    ipeCfgNtpAuthenticationAlgorithm OBJECT-TYPE
        SYNTAX       INTEGER { invalid(0), md5(1) }
        MAX-ACCESS   read-create
        STATUS       current
        DESCRIPTION  "configuring the NTP Authentication algorithm."
        ::= { ipeCfgNtpAuthenticationKeyEntry 3 }

    ipeCfgNtpAuthenticationKey OBJECT-TYPE
        SYNTAX       DisplayString (SIZE (8..128))
        MAX-ACCESS   read-create
        STATUS       current
        DESCRIPTION  
            "configuring the NTP Authentication key. This object can be
            operated in secure way."
        ::= { ipeCfgNtpAuthenticationKeyEntry 4 }

    ipeCfgNtpAuthenticationKeyId OBJECT-TYPE
        SYNTAX       Unsigned32 (1..65535)
        MAX-ACCESS   read-create
        STATUS       current
        DESCRIPTION  
            "Configuring the NTP Authentication key Identifier. The key
            identifier is used for protocol operation."
        ::= { ipeCfgNtpAuthenticationKeyEntry 5 }

    ipeCfgNtpAuthenticationKeyTrusted OBJECT-TYPE
        SYNTAX       OffOnValue
        MAX-ACCESS   read-create
        STATUS       current
        DESCRIPTION  
            "Configuring the key is trusted or not. The trusted key is ready
            to use in NTP Packets."
        ::= { ipeCfgNtpAuthenticationKeyEntry 6 }

    ipeCfgNtpAuthKeyRowStatus OBJECT-TYPE
        SYNTAX       RowStatus
        MAX-ACCESS   read-create
        STATUS       current
        DESCRIPTION  
            "This object is used to create a new row or delete an existing
            row in this table."
        ::= { ipeCfgNtpAuthenticationKeyEntry 7 }

    ipeCfgSsh OBJECT IDENTIFIER
        ::= { ipeConfigurationGroup 6 }

    ipeCfgSshServerTable OBJECT-TYPE
        SYNTAX       SEQUENCE OF IpeCfgSshServerEntry
        MAX-ACCESS   not-accessible
        STATUS       current
        DESCRIPTION  "Table of SSH configuration information."
        ::= { ipeCfgSsh 1 }

    ipeCfgSshServerEntry OBJECT-TYPE
        SYNTAX       IpeCfgSshServerEntry
        MAX-ACCESS   not-accessible
        STATUS       current
        DESCRIPTION  "Entry of SSH configuration information."
        INDEX        { ipeCfgSshServerIndex }
        ::= { ipeCfgSshServerTable 1 }

    IpeCfgSshServerEntry ::= SEQUENCE {
        ipeCfgSshServerIndex       Integer32,
        ipeCfgSshServerNEAddress   IpAddress,
        ipeCfgSshServerEnable      INTEGER,
        ipeCfgSshServerDH1024Bits  EnableDisableValue
    }

    ipeCfgSshServerIndex OBJECT-TYPE
        SYNTAX       Integer32 (1..1)
        MAX-ACCESS   not-accessible
        STATUS       current
        DESCRIPTION  "Index of table."
        ::= { ipeCfgSshServerEntry 1 }

    ipeCfgSshServerNEAddress OBJECT-TYPE
        SYNTAX       IpAddress
        MAX-ACCESS   not-accessible
        STATUS       current
        DESCRIPTION  ""
        ::= { ipeCfgSshServerEntry 2 }

    ipeCfgSshServerEnable OBJECT-TYPE
        SYNTAX       INTEGER { invalid(0), disabled(1), enabled(2) }
        MAX-ACCESS   read-write
        STATUS       current
        DESCRIPTION  "SSH control enable."
        DEFVAL       { enabled }
        ::= { ipeCfgSshServerEntry 3 }

    ipeCfgSshServerDH1024Bits OBJECT-TYPE
        SYNTAX       EnableDisableValue
        MAX-ACCESS   read-write
        STATUS       current
        DESCRIPTION  "Indicates SSH Diffie-Hellman Modulus of 1024 Bit"
        ::= { ipeCfgSshServerEntry 5 }

    ipeCfgSshClientTable OBJECT-TYPE
        SYNTAX       SEQUENCE OF IpeCfgSshClientEntry
        MAX-ACCESS   not-accessible
        STATUS       current
        DESCRIPTION  "Table of SSH configuration information."
        ::= { ipeCfgSsh 2 }

    ipeCfgSshClientEntry OBJECT-TYPE
        SYNTAX       IpeCfgSshClientEntry
        MAX-ACCESS   not-accessible
        STATUS       current
        DESCRIPTION  "Entry of SSH configuration information."
        INDEX        { ipeCfgSshClientIndex }
        ::= { ipeCfgSshClientTable 1 }

    IpeCfgSshClientEntry ::= SEQUENCE {
        ipeCfgSshClientIndex      Integer32,
        ipeCfgSshClientNEAddress  IpAddress,
        ipeCfgSshClientEnable     INTEGER
    }

    ipeCfgSshClientIndex OBJECT-TYPE
        SYNTAX       Integer32 (1..1)
        MAX-ACCESS   not-accessible
        STATUS       current
        DESCRIPTION  "Index of table."
        ::= { ipeCfgSshClientEntry 1 }

    ipeCfgSshClientNEAddress OBJECT-TYPE
        SYNTAX       IpAddress
        MAX-ACCESS   not-accessible
        STATUS       current
        DESCRIPTION  ""
        ::= { ipeCfgSshClientEntry 2 }

    ipeCfgSshClientEnable OBJECT-TYPE
        SYNTAX       INTEGER { invalid(0), disabled(1), enabled(2) }
        MAX-ACCESS   read-write
        STATUS       current
        DESCRIPTION  "SSH control enable."
        DEFVAL       { disabled }
        ::= { ipeCfgSshClientEntry 3 }

    ipeCfgFtp OBJECT IDENTIFIER
        ::= { ipeConfigurationGroup 7 }

    ipeCfgFtpServerTable OBJECT-TYPE
        SYNTAX       SEQUENCE OF IpeCfgFtpServerEntry
        MAX-ACCESS   not-accessible
        STATUS       current
        DESCRIPTION  "Table of FTP server configuration information."
        ::= { ipeCfgFtp 1 }

    ipeCfgFtpServerEntry OBJECT-TYPE
        SYNTAX       IpeCfgFtpServerEntry
        MAX-ACCESS   not-accessible
        STATUS       current
        DESCRIPTION  "Entry of FTP server configuration information."
        INDEX        { ipeCfgFtpServerIndex }
        ::= { ipeCfgFtpServerTable 1 }

    IpeCfgFtpServerEntry ::= SEQUENCE {
        ipeCfgFtpServerIndex           Integer32,
        ipeCfgFtpServerNEAddress       IpAddress,
        ipeCfgFtpServerEnable          INTEGER,
        ipeCfgFtpServerCommandTcpPort  Integer32,
        ipeCfgFtpServerDataTcpPort     Integer32,
        ipeCfgFtpServerMaxSession      Integer32,
        ipeCfgFtpServerAutoDisable     INTEGER
    }

    ipeCfgFtpServerIndex OBJECT-TYPE
        SYNTAX       Integer32 (1..1)
        MAX-ACCESS   not-accessible
        STATUS       current
        DESCRIPTION  "Index of table."
        ::= { ipeCfgFtpServerEntry 1 }

    ipeCfgFtpServerNEAddress OBJECT-TYPE
        SYNTAX       IpAddress
        MAX-ACCESS   not-accessible
        STATUS       current
        DESCRIPTION  ""
        ::= { ipeCfgFtpServerEntry 2 }

    ipeCfgFtpServerEnable OBJECT-TYPE
        SYNTAX       INTEGER {
                         invalid(0),
                         serviceDisable(1),
                         serviceEnable(2),
                         alwaysEnable(3)
                     }
        MAX-ACCESS   read-write
        STATUS       current
        DESCRIPTION  "FTP control enable."
        ::= { ipeCfgFtpServerEntry 3 }

    ipeCfgFtpServerCommandTcpPort OBJECT-TYPE
        SYNTAX       Integer32 (1..65535)
        MAX-ACCESS   read-write
        STATUS       current
        DESCRIPTION  "Port number of FTP command."
        ::= { ipeCfgFtpServerEntry 4 }

    ipeCfgFtpServerDataTcpPort OBJECT-TYPE
        SYNTAX       Integer32 (1..65535)
        MAX-ACCESS   read-write
        STATUS       current
        DESCRIPTION  "Port number of FTP data transfer."
        ::= { ipeCfgFtpServerEntry 5 }

    ipeCfgFtpServerMaxSession OBJECT-TYPE
        SYNTAX       Integer32 (1..3)
        MAX-ACCESS   read-write
        STATUS       current
        DESCRIPTION  "Number of max connections."
        ::= { ipeCfgFtpServerEntry 6 }

    ipeCfgFtpServerAutoDisable OBJECT-TYPE
        SYNTAX       INTEGER { invalid(0), disabled(1), enabled(2) }
        MAX-ACCESS   read-write
        STATUS       current
        DESCRIPTION  "FTP automatic stop control enable."
        ::= { ipeCfgFtpServerEntry 7 }

    ipeCfgSftp OBJECT IDENTIFIER
        ::= { ipeConfigurationGroup 8 }

    ipeCfgSftpServerTable OBJECT-TYPE
        SYNTAX       SEQUENCE OF IpeCfgSftpServerEntry
        MAX-ACCESS   not-accessible
        STATUS       current
        DESCRIPTION  "Table of SFTP server configuration information."
        ::= { ipeCfgSftp 1 }

    ipeCfgSftpServerEntry OBJECT-TYPE
        SYNTAX       IpeCfgSftpServerEntry
        MAX-ACCESS   not-accessible
        STATUS       current
        DESCRIPTION  "Entry of SFTP server configuration information."
        INDEX        { ipeCfgSftpServerIndex }
        ::= { ipeCfgSftpServerTable 1 }

    IpeCfgSftpServerEntry ::= SEQUENCE {
        ipeCfgSftpServerIndex        Integer32,
        ipeCfgSftpServerNEAddress    IpAddress,
        ipeCfgSftpServerEnable       INTEGER,
        ipeCfgSftpServerAutoDisable  INTEGER
    }

    ipeCfgSftpServerIndex OBJECT-TYPE
        SYNTAX       Integer32 (1..1)
        MAX-ACCESS   not-accessible
        STATUS       current
        DESCRIPTION  "Index of table."
        ::= { ipeCfgSftpServerEntry 1 }

    ipeCfgSftpServerNEAddress OBJECT-TYPE
        SYNTAX       IpAddress
        MAX-ACCESS   not-accessible
        STATUS       current
        DESCRIPTION  ""
        ::= { ipeCfgSftpServerEntry 2 }

    ipeCfgSftpServerEnable OBJECT-TYPE
        SYNTAX       INTEGER {
                         invalid(0),
                         serviceDisable(1),
                         serviceEnable(2),
                         alwaysEnable(3)
                     }
        MAX-ACCESS   read-write
        STATUS       current
        DESCRIPTION  "SFTP control enable."
        ::= { ipeCfgSftpServerEntry 3 }

    ipeCfgSftpServerAutoDisable OBJECT-TYPE
        SYNTAX       INTEGER { invalid(0), disabled(1), enabled(2) }
        MAX-ACCESS   read-write
        STATUS       current
        DESCRIPTION  "SFTP automatic stop control enable."
        ::= { ipeCfgSftpServerEntry 4 }

    ipeCfgHttp OBJECT IDENTIFIER
        ::= { ipeConfigurationGroup 9 }

    ipeCfgHttpServerTable OBJECT-TYPE
        SYNTAX       SEQUENCE OF IpeCfgHttpServerEntry
        MAX-ACCESS   not-accessible
        STATUS       current
        DESCRIPTION  "Table of HTTP configuration information."
        ::= { ipeCfgHttp 1 }

    ipeCfgHttpServerEntry OBJECT-TYPE
        SYNTAX       IpeCfgHttpServerEntry
        MAX-ACCESS   not-accessible
        STATUS       current
        DESCRIPTION  "Entry of HTTP configuration information."
        INDEX        { ipeCfgHttpServerIndex }
        ::= { ipeCfgHttpServerTable 1 }

    IpeCfgHttpServerEntry ::= SEQUENCE {
        ipeCfgHttpServerIndex      Integer32,
        ipeCfgHttpServerNEAddress  IpAddress,
        ipeCfgHttpServerEnable     INTEGER,
        ipeCfgHttpServerTcpPort    Integer32
    }

    ipeCfgHttpServerIndex OBJECT-TYPE
        SYNTAX       Integer32 (1..1)
        MAX-ACCESS   not-accessible
        STATUS       current
        DESCRIPTION  "Index of table."
        ::= { ipeCfgHttpServerEntry 1 }

    ipeCfgHttpServerNEAddress OBJECT-TYPE
        SYNTAX       IpAddress
        MAX-ACCESS   not-accessible
        STATUS       current
        DESCRIPTION  ""
        ::= { ipeCfgHttpServerEntry 2 }

    ipeCfgHttpServerEnable OBJECT-TYPE
        SYNTAX       INTEGER { invalid(0), disabled(1), enabled(2) }
        MAX-ACCESS   read-write
        STATUS       current
        DESCRIPTION  "HTTP control enable."
        ::= { ipeCfgHttpServerEntry 3 }

    ipeCfgHttpServerTcpPort OBJECT-TYPE
        SYNTAX       Integer32 (1..65535)
        MAX-ACCESS   read-write
        STATUS       current
        DESCRIPTION  "Port number of HTTP."
        ::= { ipeCfgHttpServerEntry 4 }

    ipeCfgHttps OBJECT IDENTIFIER
        ::= { ipeConfigurationGroup 10 }

    ipeCfgHttpsServerTable OBJECT-TYPE
        SYNTAX       SEQUENCE OF IpeCfgHttpsServerEntry
        MAX-ACCESS   not-accessible
        STATUS       current
        DESCRIPTION  "Table of HTTPS configuration information."
        ::= { ipeCfgHttps 1 }

    ipeCfgHttpsServerEntry OBJECT-TYPE
        SYNTAX       IpeCfgHttpsServerEntry
        MAX-ACCESS   not-accessible
        STATUS       current
        DESCRIPTION  "Entry of HTTPS configuration information."
        INDEX        { ipeCfgHttpsServerIndex }
        ::= { ipeCfgHttpsServerTable 1 }

    IpeCfgHttpsServerEntry ::= SEQUENCE {
        ipeCfgHttpsServerIndex      Integer32,
        ipeCfgHttpsServerNEAddress  IpAddress,
        ipeCfgHttpsServerEnable     INTEGER,
        ipeCfgHttpsServerTcpPort    Integer32
    }

    ipeCfgHttpsServerIndex OBJECT-TYPE
        SYNTAX       Integer32 (1..1)
        MAX-ACCESS   not-accessible
        STATUS       current
        DESCRIPTION  "Index of table."
        ::= { ipeCfgHttpsServerEntry 1 }

    ipeCfgHttpsServerNEAddress OBJECT-TYPE
        SYNTAX       IpAddress
        MAX-ACCESS   not-accessible
        STATUS       current
        DESCRIPTION  ""
        ::= { ipeCfgHttpsServerEntry 2 }

    ipeCfgHttpsServerEnable OBJECT-TYPE
        SYNTAX       INTEGER { invalid(0), disabled(1), enabled(2) }
        MAX-ACCESS   read-write
        STATUS       current
        DESCRIPTION  "HTTPS control enable."
        ::= { ipeCfgHttpsServerEntry 3 }

    ipeCfgHttpsServerTcpPort OBJECT-TYPE
        SYNTAX       Integer32 (1..65535)
        MAX-ACCESS   read-write
        STATUS       current
        DESCRIPTION  "TCP port number of HTTPS."
        ::= { ipeCfgHttpsServerEntry 4 }

    ipeCfgHttpsRsaTable OBJECT-TYPE
        SYNTAX       SEQUENCE OF IpeCfgHttpsRsaEntry
        MAX-ACCESS   not-accessible
        STATUS       current
        DESCRIPTION  "Table of HTTPS RSA configuration information."
        ::= { ipeCfgHttps 2 }

    ipeCfgHttpsRsaEntry OBJECT-TYPE
        SYNTAX       IpeCfgHttpsRsaEntry
        MAX-ACCESS   not-accessible
        STATUS       current
        DESCRIPTION  "Entry of HTTPS RSA configuration information."
        INDEX        { ipeCfgHttpsRsaIndex }
        ::= { ipeCfgHttpsRsaTable 1 }

    IpeCfgHttpsRsaEntry ::= SEQUENCE {
        ipeCfgHttpsRsaIndex             Integer32,
        ipeCfgHttpsRsaNEAddress         IpAddress,
        ipeCfgHttpsRsaPassPhrase        DisplayString,
        ipeCfgHttpsRsaEncryptAlgorithm  INTEGER
    }

    ipeCfgHttpsRsaIndex OBJECT-TYPE
        SYNTAX       Integer32 (1..1)
        MAX-ACCESS   not-accessible
        STATUS       current
        DESCRIPTION  "Index of table."
        ::= { ipeCfgHttpsRsaEntry 1 }

    ipeCfgHttpsRsaNEAddress OBJECT-TYPE
        SYNTAX       IpAddress
        MAX-ACCESS   not-accessible
        STATUS       current
        DESCRIPTION  ""
        ::= { ipeCfgHttpsRsaEntry 2 }

    ipeCfgHttpsRsaPassPhrase OBJECT-TYPE
        SYNTAX       DisplayString (SIZE(8..128))
        MAX-ACCESS   read-write
        STATUS       current
        DESCRIPTION  
            "Pass-phrase for the RSA private key. The valid length of user
            input value must be 8 to 64 chars.  After the encryption, the
            contents will be changed, and the length might be longer than 64
            chars."
        ::= { ipeCfgHttpsRsaEntry 3 }

    ipeCfgHttpsRsaEncryptAlgorithm OBJECT-TYPE
        SYNTAX       INTEGER {
                         invalid(0),
                         aes128(1),
                         aes192(2),
                         aes256(3),
                         camellia128(4),
                         camellia192(5),
                         camellia256(6),
                         des3(7)
                     }
        MAX-ACCESS   read-write
        STATUS       current
        DESCRIPTION  "Encryption algorithm for the RSA private key."
        ::= { ipeCfgHttpsRsaEntry 4 }

    ipeCfgHttpsCsrTable OBJECT-TYPE
        SYNTAX       SEQUENCE OF IpeCfgHttpsCsrEntry
        MAX-ACCESS   not-accessible
        STATUS       current
        DESCRIPTION  "Table of HTTPS CSR configuration information."
        ::= { ipeCfgHttps 3 }

    ipeCfgHttpsCsrEntry OBJECT-TYPE
        SYNTAX       IpeCfgHttpsCsrEntry
        MAX-ACCESS   not-accessible
        STATUS       current
        DESCRIPTION  "Entry of HTTPS CSR configuration information."
        INDEX        { ipeCfgHttpsCsrIndex }
        ::= { ipeCfgHttpsCsrTable 1 }

    IpeCfgHttpsCsrEntry ::= SEQUENCE {
        ipeCfgHttpsCsrIndex                   Integer32,
        ipeCfgHttpsCsrNEAddress               IpAddress,
        ipeCfgHttpsCsrRsaPassPhrase           DisplayString,
        ipeCfgHttpsCsrMessageDigestAlgorithm  INTEGER,
        ipeCfgHttpsCsrCountry                 DisplayString,
        ipeCfgHttpsCsrState                   DisplayString,
        ipeCfgHttpsCsrLocality                DisplayString,
        ipeCfgHttpsCsrOrganization            DisplayString,
        ipeCfgHttpsCsrOrganizationalUnit      DisplayString,
        ipeCfgHttpsCsrCommonName              DisplayString
    }

    ipeCfgHttpsCsrIndex OBJECT-TYPE
        SYNTAX       Integer32 (1..1)
        MAX-ACCESS   not-accessible
        STATUS       current
        DESCRIPTION  "Index of table."
        ::= { ipeCfgHttpsCsrEntry 1 }

    ipeCfgHttpsCsrNEAddress OBJECT-TYPE
        SYNTAX       IpAddress
        MAX-ACCESS   not-accessible
        STATUS       current
        DESCRIPTION  ""
        ::= { ipeCfgHttpsCsrEntry 2 }

    ipeCfgHttpsCsrRsaPassPhrase OBJECT-TYPE
        SYNTAX       DisplayString (SIZE(8..128))
        MAX-ACCESS   read-write
        STATUS       current
        DESCRIPTION  
            "Pass-phrase for the RSA private key. This is same as
            ipeCfgHttpsRsaPassPhrase."
        ::= { ipeCfgHttpsCsrEntry 3 }

    ipeCfgHttpsCsrMessageDigestAlgorithm OBJECT-TYPE
        SYNTAX       INTEGER {
                         invalid(0),
                         sha224(1),
                         sha256(2),
                         sha384(3),
                         sha512(4)
                     }
        MAX-ACCESS   read-write
        STATUS       current
        DESCRIPTION  "Message Digest algorithm for the CSR."
        ::= { ipeCfgHttpsCsrEntry 4 }

    ipeCfgHttpsCsrCountry OBJECT-TYPE
        SYNTAX       DisplayString (SIZE(2..2))
        MAX-ACCESS   read-write
        STATUS       current
        DESCRIPTION  "HTTPS CSR country name. 2 letter code. eg, US."
        ::= { ipeCfgHttpsCsrEntry 5 }

    ipeCfgHttpsCsrState OBJECT-TYPE
        SYNTAX       DisplayString (SIZE(2..64))
        MAX-ACCESS   read-write
        STATUS       current
        DESCRIPTION  
            "HTTPS CSR state or province name. eg, California (full name)."
        ::= { ipeCfgHttpsCsrEntry 6 }

    ipeCfgHttpsCsrLocality OBJECT-TYPE
        SYNTAX       DisplayString (SIZE(2..64))
        MAX-ACCESS   read-write
        STATUS       current
        DESCRIPTION  "HTTPS CSR locality name. eg, Saint Louis (city)."
        ::= { ipeCfgHttpsCsrEntry 7 }

    ipeCfgHttpsCsrOrganization OBJECT-TYPE
        SYNTAX       DisplayString (SIZE(2..64))
        MAX-ACCESS   read-write
        STATUS       current
        DESCRIPTION  "HTTPS CSR organization. eg, NEC Corporation."
        ::= { ipeCfgHttpsCsrEntry 8 }

    ipeCfgHttpsCsrOrganizationalUnit OBJECT-TYPE
        SYNTAX       DisplayString (SIZE(2..64))
        MAX-ACCESS   read-write
        STATUS       current
        DESCRIPTION  
            "HTTPS CSR organizational unit. eg, SSL Department (section)."
        ::= { ipeCfgHttpsCsrEntry 9 }

    ipeCfgHttpsCsrCommonName OBJECT-TYPE
        SYNTAX       DisplayString (SIZE(2..64))
        MAX-ACCESS   read-write
        STATUS       current
        DESCRIPTION  
            "HTTPS CSR common name. eg, apache.netsure.net (your name or your
            server's hostname)."
        ::= { ipeCfgHttpsCsrEntry 10 }

    ipeCfgSnmp OBJECT IDENTIFIER
        ::= { ipeConfigurationGroup 11 }

    ipeCfgSnmpServerTable OBJECT-TYPE
        SYNTAX       SEQUENCE OF IpeCfgSnmpServerEntry
        MAX-ACCESS   not-accessible
        STATUS       current
        DESCRIPTION  "A table of SNMP configuration information."
        ::= { ipeCfgSnmp 1 }

    ipeCfgSnmpServerEntry OBJECT-TYPE
        SYNTAX       IpeCfgSnmpServerEntry
        MAX-ACCESS   not-accessible
        STATUS       current
        DESCRIPTION  "A set of SNMP configuration information."
        INDEX        { ipeCfgSnmpServerIndex }
        ::= { ipeCfgSnmpServerTable 1 }

    IpeCfgSnmpServerEntry ::= SEQUENCE {
        ipeCfgSnmpServerIndex       Integer32,
        ipeCfgSnmpServerNEAddress   IpAddress,
        ipeCfgSnmpV1V2cEnable       INTEGER,
        ipeCfgSnmpV3Enable          INTEGER,
        ipeCfgSnmpServerPort        Integer32,
        ipeCfgSnmpServerToBigError  Integer32,
        ipeCfgSnmpV1AccessMode      INTEGER
    }

    ipeCfgSnmpServerIndex OBJECT-TYPE
        SYNTAX       Integer32 (1..1)
        MAX-ACCESS   not-accessible
        STATUS       current
        DESCRIPTION  
            "Index of this ipeCfgSnmpServerEntry.
            It's a fiexed value(= 1)."
        ::= { ipeCfgSnmpServerEntry 1 }

    ipeCfgSnmpServerNEAddress OBJECT-TYPE
        SYNTAX       IpAddress
        MAX-ACCESS   not-accessible
        STATUS       current
        DESCRIPTION  ""
        ::= { ipeCfgSnmpServerEntry 2 }

    ipeCfgSnmpV1V2cEnable OBJECT-TYPE
        SYNTAX       INTEGER { invalid(0), disabled(1), enabled(2) }
        MAX-ACCESS   read-write
        STATUS       current
        DESCRIPTION  
            "Indicates the SNMP entity is permitted to receive & process
            SNMPv1/v2c PDU or is not permitted to do.
            
            Even if it is disabled, SNMPv1/v2c Traps is sent."
        ::= { ipeCfgSnmpServerEntry 3 }

    ipeCfgSnmpV3Enable OBJECT-TYPE
        SYNTAX       INTEGER { invalid(0), disabled(1), enabled(2) }
        MAX-ACCESS   read-write
        STATUS       current
        DESCRIPTION  
            "Indicates the SNMP entity is permitted to receive & process
            SNMPv3 PDU or is not permitted to do.
            
            Even if it is disabled, SNMPv3 Traps is sent."
        ::= { ipeCfgSnmpServerEntry 4 }

    ipeCfgSnmpServerPort OBJECT-TYPE
        SYNTAX       Integer32 (1..65535)
        MAX-ACCESS   read-write
        STATUS       current
        DESCRIPTION  
            "A UDP port number to receive all SNMP Request-PDU.
            The reboot of the system is necessary to reflect setting."
        ::= { ipeCfgSnmpServerEntry 5 }

    ipeCfgSnmpServerToBigError OBJECT-TYPE
        SYNTAX       Integer32
        MAX-ACCESS   read-write
        STATUS       obsolete
        DESCRIPTION  
            "Indicates the PDU size of SNMP Too Big Error Response."
        ::= { ipeCfgSnmpServerEntry 6 }

    ipeCfgSnmpV1AccessMode OBJECT-TYPE
        SYNTAX       INTEGER { invalid(0), standardMode(1), proprietaryMode(2) }
        MAX-ACCESS   read-write
        STATUS       current
        DESCRIPTION  "Indicates SNMPv1 Access Mode."
        ::= { ipeCfgSnmpServerEntry 7 }

    ipeCfgSnmpCommunityTable OBJECT-TYPE
        SYNTAX       SEQUENCE OF IpeCfgSnmpCommunityEntry
        MAX-ACCESS   not-accessible
        STATUS       current
        DESCRIPTION  "A table of SNMP community information."
        ::= { ipeCfgSnmp 2 }

    ipeCfgSnmpCommunityEntry OBJECT-TYPE
        SYNTAX       IpeCfgSnmpCommunityEntry
        MAX-ACCESS   not-accessible
        STATUS       current
        DESCRIPTION  "A set of SNMP community information."
        INDEX        { ipeCfgSnmpCommunityIndex }
        ::= { ipeCfgSnmpCommunityTable 1 }

    IpeCfgSnmpCommunityEntry ::= SEQUENCE {
        ipeCfgSnmpCommunityIndex                  Integer32,
        ipeCfgSnmpCommunityNEAddress              IpAddress,
        ipeCfgSnmpCommunityName                   DisplayString,
        ipeCfgSnmpCommunityAccessLevel            INTEGER,
        ipeCfgSnmpCommunityAccessAddress          IpAddress,
        ipeCfgSnmpCommunityAccessPrefixLength     Integer32,
        ipeCfgSnmpCommunityRowStatus              RowStatus,
        ipeCfgSnmpCommunityAccessAddress2         IpAddress,
        ipeCfgSnmpCommunityAccessPrefixLength2    Integer32,
        ipeCfgSnmpCommunityAccessAddress3         IpAddress,
        ipeCfgSnmpCommunityAccessPrefixLength3    Integer32,
        ipeCfgSnmpCommunityAccessUsage            UsedNotusedValue,
        ipeCfgSnmpCommunityAccessUsage2           UsedNotusedValue,
        ipeCfgSnmpCommunityAccessUsage3           UsedNotusedValue,
        ipeCfgSnmpCommunityAccessV6Address        Ipv6Address,
        ipeCfgSnmpCommunityAccessV6PrefixLength   Integer32,
        ipeCfgSnmpCommunityAccessV6Address2       Ipv6Address,
        ipeCfgSnmpCommunityAccessV6PrefixLength2  Integer32,
        ipeCfgSnmpCommunityAccessV6Address3       Ipv6Address,
        ipeCfgSnmpCommunityAccessV6PrefixLength3  Integer32,
        ipeCfgSnmpCommunityAccessAddressType      INTEGER,
        ipeCfgSnmpCommunityAccessV6Usage          UsedNotusedValue,
        ipeCfgSnmpCommunityAccessV6Usage2         UsedNotusedValue,
        ipeCfgSnmpCommunityAccessV6Usage3         UsedNotusedValue
    }

    ipeCfgSnmpCommunityIndex OBJECT-TYPE
        SYNTAX       Integer32 (1..10)
        MAX-ACCESS   not-accessible
        STATUS       current
        DESCRIPTION  
            "Index of this ipeCfgSnmpCommunityEntry.
            You have to choose a value  from 1 to 10."
        ::= { ipeCfgSnmpCommunityEntry 1 }

    ipeCfgSnmpCommunityNEAddress OBJECT-TYPE
        SYNTAX       IpAddress
        MAX-ACCESS   not-accessible
        STATUS       current
        DESCRIPTION  ""
        ::= { ipeCfgSnmpCommunityEntry 2 }

    ipeCfgSnmpCommunityName OBJECT-TYPE
        SYNTAX       DisplayString (SIZE(1..31))
        MAX-ACCESS   read-create
        STATUS       current
        DESCRIPTION  
            "This entity's community name.
            
            Please use ASCII code."
        ::= { ipeCfgSnmpCommunityEntry 3 }

    ipeCfgSnmpCommunityAccessLevel OBJECT-TYPE
        SYNTAX       INTEGER {
                         invalid(0),
                         operatorLevel(1),
                         configLevel(2),
                         adminLevel(3),
                         debugLevel(4)
                     }
        MAX-ACCESS   read-create
        STATUS       current
        DESCRIPTION  
            "A access level of a connection using this entry's community
            name."
        ::= { ipeCfgSnmpCommunityEntry 4 }

    ipeCfgSnmpCommunityAccessAddress OBJECT-TYPE
        SYNTAX       IpAddress
        MAX-ACCESS   read-create
        STATUS       current
        DESCRIPTION  
            "An address which is permitted to use this entry's community
            name.
            When masking in ipeCfgSnmpCommunityAccessPrefixLength, the host
            address part has to be a zero, if any.
            
            Also the following address can't be used.
            127.0.0.0/8 Loopback
            224.0.0.0/4 Multicasts (former Class D)
            240.0.0.0/4 Reserved (former Class E)"
        ::= { ipeCfgSnmpCommunityEntry 5 }

    ipeCfgSnmpCommunityAccessPrefixLength OBJECT-TYPE
        SYNTAX       Integer32 (0..32)
        MAX-ACCESS   read-create
        STATUS       current
        DESCRIPTION  "A prefix length of ipeCfgSnmpCommunityAccessAddress."
        ::= { ipeCfgSnmpCommunityEntry 6 }

    ipeCfgSnmpCommunityRowStatus OBJECT-TYPE
        SYNTAX       RowStatus { active(1), createAndGo(4), destroy(6) }
        MAX-ACCESS   read-create
        STATUS       current
        DESCRIPTION  
            "This RowStatus has a status only  active(1).
            You can SET only createAndGo(4) or Destroy(6).
            
            1) how to create
            To create a new row, you must SET objects indicated below.
            
            ipeCfgSnmpCommunityName
            ipeCfgSnmpCommunityAccessLevel
            ipeCfgSnmpCommunityAccessAddress
            ipeCfgSnmpCommunityAccessPrefixLength
            ipeCfgSnmpCommunityAccessAddress2 *
            ipeCfgSnmpCommunityAccessPrefixLength2 *
            ipeCfgSnmpCommunityAccessAddress3 *
            ipeCfgSnmpCommunityAccessPrefixLength3 *
            ipeCfgSnmpCommunityAccessUsage *
            ipeCfgSnmpCommunityAccessUsage2 *
            ipeCfgSnmpCommunityAccessUsage3 *
            ipeCfgSnmpCommunityAccessV6Address
            ipeCfgSnmpCommunityAccessV6PrefixLength
            ipeCfgSnmpCommunityAccessV6Address2 *
            ipeCfgSnmpCommunityAccessV6PrefixLength2 *
            ipeCfgSnmpCommunityAccessV6Address3 *
            ipeCfgSnmpCommunityAccessV6PrefixLength3 *
            ipeCfgSnmpCommunityAccessAddressType *
            ipeCfgSnmpCommunityAccessV6Usage *
            ipeCfgSnmpCommunityAccessV6Usage2 *
            ipeCfgSnmpCommunityAccessV6Usage3 *
            ipeCfgSnmpCommunityRowStatus <- createAndGo(4)
            
            * NOT for EX CPRI
            
            Either ipeCfgSnmpCommunityAccessAddress/Address2/Address3 or 
            ipeCfgSnmpCommunityAccessV6Address/Address2/Address3 can be 
            configured depending on ipeCfgSnmpCommunityAccessAddressType.
            
            ipeCfgSnmpCommunityIndex is an index of this entry.
             
            2) how to destroy
            To destroy a exist row, you must SET a destory(6) to
            ipeCfgSnmpCommunityRowStatus.
            
            3) how to modify
            It is not possible.
            Please destroy a exist row, and create a new row.
            < Attention >
            You have to restart equipment to apply this entry(creating,
            deleting) to actual movement."
        ::= { ipeCfgSnmpCommunityEntry 7 }

    ipeCfgSnmpCommunityAccessAddress2 OBJECT-TYPE
        SYNTAX       IpAddress
        MAX-ACCESS   read-create
        STATUS       current
        DESCRIPTION  
            "An address which is permitted to use this entry's community
            name.
            When masking in ipeCfgSnmpCommunityAccessPrefixLength, the host
            address part has to be a zero, if any.
            
            Also the following address can't be used.
            127.0.0.0/8 Loopback
            224.0.0.0/4 Multicasts (former Class D)
            240.0.0.0/4 Reserved (former Class E)"
        ::= { ipeCfgSnmpCommunityEntry 8 }

    ipeCfgSnmpCommunityAccessPrefixLength2 OBJECT-TYPE
        SYNTAX       Integer32 (0..32)
        MAX-ACCESS   read-create
        STATUS       current
        DESCRIPTION  "A prefix length of ipeCfgSnmpCommunityAccessAddress."
        ::= { ipeCfgSnmpCommunityEntry 9 }

    ipeCfgSnmpCommunityAccessAddress3 OBJECT-TYPE
        SYNTAX       IpAddress
        MAX-ACCESS   read-create
        STATUS       current
        DESCRIPTION  
            "An address which is permitted to use this entry's community
            name.
            When masking in ipeCfgSnmpCommunityAccessPrefixLength, the host
            address part has to be a zero, if any.
            
            Also the following address can't be used.
            127.0.0.0/8 Loopback
            224.0.0.0/4 Multicasts (former Class D)
            240.0.0.0/4 Reserved (former Class E)"
        ::= { ipeCfgSnmpCommunityEntry 10 }

    ipeCfgSnmpCommunityAccessPrefixLength3 OBJECT-TYPE
        SYNTAX       Integer32 (0..32)
        MAX-ACCESS   read-create
        STATUS       current
        DESCRIPTION  "A prefix length of ipeCfgSnmpCommunityAccessAddress."
        ::= { ipeCfgSnmpCommunityEntry 11 }

    ipeCfgSnmpCommunityAccessUsage OBJECT-TYPE
        SYNTAX       UsedNotusedValue
        MAX-ACCESS   read-create
        STATUS       current
        DESCRIPTION  "Access Control Usage."
        DEFVAL       { notUsed }
        ::= { ipeCfgSnmpCommunityEntry 12 }

    ipeCfgSnmpCommunityAccessUsage2 OBJECT-TYPE
        SYNTAX       UsedNotusedValue
        MAX-ACCESS   read-create
        STATUS       current
        DESCRIPTION  "Access Control Usage."
        DEFVAL       { notUsed }
        ::= { ipeCfgSnmpCommunityEntry 13 }

    ipeCfgSnmpCommunityAccessUsage3 OBJECT-TYPE
        SYNTAX       UsedNotusedValue
        MAX-ACCESS   read-create
        STATUS       current
        DESCRIPTION  "Access Control Usage."
        DEFVAL       { notUsed }
        ::= { ipeCfgSnmpCommunityEntry 14 }

    ipeCfgSnmpCommunityAccessV6Address OBJECT-TYPE
        SYNTAX       Ipv6Address
        MAX-ACCESS   read-create
        STATUS       current
        DESCRIPTION  
            "An IPv6 address which is permitted to use this entry's community
            name.
            The following are not valid addresses:
              ::1/128 IPv6 Loopback
              FF00::/8 IPv6 Multicasts
              FE80::/10 Link local"
        ::= { ipeCfgSnmpCommunityEntry 15 }

    ipeCfgSnmpCommunityAccessV6PrefixLength OBJECT-TYPE
        SYNTAX       Integer32 (0..128)
        MAX-ACCESS   read-create
        STATUS       current
        DESCRIPTION  
            "A prefix length of ipeCfgSnmpCommunityAccessV6Address."
        ::= { ipeCfgSnmpCommunityEntry 16 }

    ipeCfgSnmpCommunityAccessV6Address2 OBJECT-TYPE
        SYNTAX       Ipv6Address
        MAX-ACCESS   read-create
        STATUS       current
        DESCRIPTION  
            "An IPv6 address which is permitted to use this entry's community
            name.
            The following are not valid addresses 
              ::1/128 IPv6 Loopback
              FF00::/8 IPv6 Multicasts
              FE80::/10 Link local"
        ::= { ipeCfgSnmpCommunityEntry 17 }

    ipeCfgSnmpCommunityAccessV6PrefixLength2 OBJECT-TYPE
        SYNTAX       Integer32 (0..128)
        MAX-ACCESS   read-create
        STATUS       current
        DESCRIPTION  
            "A prefix length of ipeCfgSnmpCommunityAccessV6Address."
        ::= { ipeCfgSnmpCommunityEntry 18 }

    ipeCfgSnmpCommunityAccessV6Address3 OBJECT-TYPE
        SYNTAX       Ipv6Address
        MAX-ACCESS   read-create
        STATUS       current
        DESCRIPTION  
            "An IPv6 address which is permitted to use this entry's community
            name.
            The following are not valid addresses 
              ::1/128 IPv6 Loopback
              FF00::/8 IPv6 Multicasts
              FE80::/10 Link local"
        ::= { ipeCfgSnmpCommunityEntry 19 }

    ipeCfgSnmpCommunityAccessV6PrefixLength3 OBJECT-TYPE
        SYNTAX       Integer32 (0..128)
        MAX-ACCESS   read-create
        STATUS       current
        DESCRIPTION  
            "A prefix length of ipeCfgSnmpCommunityAccessV6Address."
        ::= { ipeCfgSnmpCommunityEntry 20 }

    ipeCfgSnmpCommunityAccessAddressType OBJECT-TYPE
        SYNTAX       INTEGER { invalid(0), ipv4(1), ipv6(2) }
        MAX-ACCESS   read-create
        STATUS       current
        DESCRIPTION  "An address type to be used for the community access."
        ::= { ipeCfgSnmpCommunityEntry 21 }

    ipeCfgSnmpCommunityAccessV6Usage OBJECT-TYPE
        SYNTAX       UsedNotusedValue
        MAX-ACCESS   read-create
        STATUS       current
        DESCRIPTION  "Access Control IPv6 Usage."
        ::= { ipeCfgSnmpCommunityEntry 22 }

    ipeCfgSnmpCommunityAccessV6Usage2 OBJECT-TYPE
        SYNTAX       UsedNotusedValue
        MAX-ACCESS   read-create
        STATUS       current
        DESCRIPTION  "Access Control IPv6 Usage."
        ::= { ipeCfgSnmpCommunityEntry 23 }

    ipeCfgSnmpCommunityAccessV6Usage3 OBJECT-TYPE
        SYNTAX       UsedNotusedValue
        MAX-ACCESS   read-create
        STATUS       current
        DESCRIPTION  "Access Control IPv6 Usage."
        ::= { ipeCfgSnmpCommunityEntry 24 }

    ipeCfgSnmpTrapTable OBJECT-TYPE
        SYNTAX       SEQUENCE OF IpeCfgSnmpTrapEntry
        MAX-ACCESS   not-accessible
        STATUS       current
        DESCRIPTION  "A table of notification information."
        ::= { ipeCfgSnmp 3 }

    ipeCfgSnmpTrapEntry OBJECT-TYPE
        SYNTAX       IpeCfgSnmpTrapEntry
        MAX-ACCESS   not-accessible
        STATUS       current
        DESCRIPTION  "A set of notification information."
        INDEX        { ipeCfgSnmpTrapEntryIndex }
        ::= { ipeCfgSnmpTrapTable 1 }

    IpeCfgSnmpTrapEntry ::= SEQUENCE {
        ipeCfgSnmpTrapEntryIndex         Integer32,
        ipeCfgSnmpTrapEntryNEAddress     IpAddress,
        ipeCfgSnmpTrapVersion            INTEGER,
        ipeCfgSnmpTrapNotifyType         INTEGER,
        ipeCfgSnmpTrapTargetAddress      IpAddress,
        ipeCfgSnmpTrapTargetPort         Integer32,
        ipeCfgSnmpTrapSecurityName       DisplayString,
        ipeCfgSnmpTrapSecurityLevel      INTEGER,
        ipeCfgSnmpTrapEngineId           OCTET STRING,
        ipeCfgSnmpTrapAuthAlgorithm      INTEGER,
        ipeCfgSnmpTrapAuthKey            DisplayString,
        ipeCfgSnmpTrapPrivAlgorithm      INTEGER,
        ipeCfgSnmpTrapPrivKey            DisplayString,
        ipeCfgSnmpTrapRowStatus          RowStatus,
        ipeCfgSnmpTrapTargetV6Address    Ipv6Address,
        ipeCfgSnmpTrapTargetIfIndex      INTEGER,
        ipeCfgSnmpTrapTargetAddressType  INTEGER
    }

    ipeCfgSnmpTrapEntryIndex OBJECT-TYPE
        SYNTAX       Integer32 (1..6)
        MAX-ACCESS   not-accessible
        STATUS       current
        DESCRIPTION  
            "Index of this ipeCfgSnmpTrapEntry.
            You have to choose a value from 1 to 6.
            
            The entry by which an index is 4,5 and 6 is volatile. Those entry
            is eliminated at the equipment reboot."
        ::= { ipeCfgSnmpTrapEntry 1 }

    ipeCfgSnmpTrapEntryNEAddress OBJECT-TYPE
        SYNTAX       IpAddress
        MAX-ACCESS   not-accessible
        STATUS       current
        DESCRIPTION  ""
        ::= { ipeCfgSnmpTrapEntry 2 }

    ipeCfgSnmpTrapVersion OBJECT-TYPE
        SYNTAX       INTEGER { invalid(0), v1(1), v2c(2), v3(3) }
        MAX-ACCESS   read-create
        STATUS       current
        DESCRIPTION  "A version of this entry's notification."
        ::= { ipeCfgSnmpTrapEntry 3 }

    ipeCfgSnmpTrapNotifyType OBJECT-TYPE
        SYNTAX       INTEGER { invalid(0), trap(1), inform(2) }
        MAX-ACCESS   read-create
        STATUS       current
        DESCRIPTION  "A notification type of this entry's notification."
        ::= { ipeCfgSnmpTrapEntry 4 }

    ipeCfgSnmpTrapTargetAddress OBJECT-TYPE
        SYNTAX       IpAddress
        MAX-ACCESS   read-create
        STATUS       current
        DESCRIPTION  
            "Destination IP address of this entry's notification.
            
            The following address can't be used.
            127.0.0.0/8 Loopback
            0.0.0.0/0    Current network
            224.0.0.0/4 Multicasts (former Class D)
            240.0.0.0/4 Reserved (former Class E)"
        ::= { ipeCfgSnmpTrapEntry 5 }

    ipeCfgSnmpTrapTargetPort OBJECT-TYPE
        SYNTAX       Integer32 (1..65535)
        MAX-ACCESS   read-create
        STATUS       current
        DESCRIPTION  "Destination UDP port this entry's notification."
        ::= { ipeCfgSnmpTrapEntry 6 }

    ipeCfgSnmpTrapSecurityName OBJECT-TYPE
        SYNTAX       DisplayString (SIZE(1..31))
        MAX-ACCESS   read-create
        STATUS       current
        DESCRIPTION  
            "A security name.
            The meaning is different depending on ipeCfgSnmpTrapVersion.
            
            v1/v2c  : It's meaning a community name.
            v3      : It's meaning a user name.
            
            Please use ASCII code.
            
            The characters which can be used are '-', '_','0'-'9', 'a'-'z'
            and 'A'-'Z'.
            
            When there was the same combination to the other index,
            ipeCfgSnmpTrapSecurityName and ipeCfgSnmpTrapEngineId become
            error."
        ::= { ipeCfgSnmpTrapEntry 7 }

    ipeCfgSnmpTrapSecurityLevel OBJECT-TYPE
        SYNTAX       INTEGER {
                         invalid(0),
                         noAuthNoPriv(1),
                         authNoPriv(2),
                         authPriv(3)
                     }
        MAX-ACCESS   read-create
        STATUS       current
        DESCRIPTION  
            "A security level of this entry's notification.
            
            When ipeCfgSnmpTrapVersion is v1(1) or v2c(2), you have to SET
            noAuthNoPriv(1)."
        ::= { ipeCfgSnmpTrapEntry 8 }

    ipeCfgSnmpTrapEngineId OBJECT-TYPE
        SYNTAX       OCTET STRING (SIZE(5..32))
        MAX-ACCESS   read-create
        STATUS       current
        DESCRIPTION  
            "A snmpEngineID which this entry's notification uses.(5-32 octet)
            ipeCfgSnmpTrapNotifyType is effective only at the time of
            inform(2).
            A snmpEngineID of a destination SNMP entity.
            
            When there was the same combination to the other index,
            ipeCfgSnmpTrapSecurityName and ipeCfgSnmpTrapEngineId become
            error."
        ::= { ipeCfgSnmpTrapEntry 9 }

    ipeCfgSnmpTrapAuthAlgorithm OBJECT-TYPE
        SYNTAX       INTEGER { invalid(0), md5(1), sha(2) }
        MAX-ACCESS   read-create
        STATUS       current
        DESCRIPTION  
            "Authentication protocol.
            
            ipeCfgSnmpTrapNotifyType is effective for the SET only at the
            time of inform(2). Even if it is done SET in the case of trap(1),
            I am ignored. In addition, a value of
            ipeCfgAccountUserSnmpV3AuthAlgorithm is acquired at time to get."
        ::= { ipeCfgSnmpTrapEntry 10 }

    ipeCfgSnmpTrapAuthKey OBJECT-TYPE
        SYNTAX       DisplayString (SIZE(8..128))
        MAX-ACCESS   read-create
        STATUS       current
        DESCRIPTION  
            "Authenticate password for SNMP inform PDU.
            This object can be operated only when in secure way. 
            When the object 'ipeCfgSnmpTrapNotifyType' is trap(1), SET
            request is not processed (discarded), and GET request returns the
            same value as 'ipeCfgAccountUserSnmpV3AuthKey'."
        ::= { ipeCfgSnmpTrapEntry 11 }

    ipeCfgSnmpTrapPrivAlgorithm OBJECT-TYPE
        SYNTAX       INTEGER { invalid(0), des(1), aes(2) }
        MAX-ACCESS   read-create
        STATUS       current
        DESCRIPTION  
            "privacy protocol.
            
            ipeCfgSnmpTrapNotifyType is effective for the SET only at the
            time of inform(2). Even if it is done SET in the case of trap(1),
            I am ignored. In addition, a value of
            ipeCfgAccountUserSnmpV3PrivAlgorithm is acquired at time to get."
        ::= { ipeCfgSnmpTrapEntry 12 }

    ipeCfgSnmpTrapPrivKey OBJECT-TYPE
        SYNTAX       DisplayString (SIZE(8..128))
        MAX-ACCESS   read-create
        STATUS       current
        DESCRIPTION  
            "Privacy password for SNMP inform PDU.
            This objet can be operated only when in secure way. 
            When the object 'ipeCfgSnmpTrapNotifyType' is trap(1), SET
            request is not processed (discarded), and GET request returns the
            same value as 'ipeCfgAccountUserSnmpV3PrivKey'."
        ::= { ipeCfgSnmpTrapEntry 13 }

    ipeCfgSnmpTrapRowStatus OBJECT-TYPE
        SYNTAX       RowStatus { active(1), createAndGo(4), destroy(6) }
        MAX-ACCESS   read-create
        STATUS       current
        DESCRIPTION  
            "This RowStatus has a status only  active(1).
            You can SET only createAndGo(4) or destroy(6).
            
            1) how to create
            1.1) SNMPv1/v2c
            To create a new row, you must SET objects indicated below.
            
            ipeCfgSnmpTrapEntryIndex, ipeCfgSnmpTrapVersion,
            ipeCfgSnmpTrapNotifyType, ipeCfgSnmpTrapTargetAddress,
            ipeCfgSnmpTrapTargetV6Address,
            ipeCfgSnmpTrapTargetAddressType(*), ipeCfgSnmpTrapTaergetPort,
            ipeCfgSnmpTrapSecurityName
            ipeCfgSnmpTrapRowStatus     # Only createAndGo(4).
            
            It isn't necessary to set ipeCfgSnmpTrapSecurityLevel. When set
            it, the value is checked, so all except for noAuthNoPriv (1) will
            be NG.
            And, the other object is not necessary. Even if it is done SET,
            it is checked the value, but ignored.
            
            1.2) SNMPv3 (ipeCfgSnmpTrapNotifyType = trap(1))
            ipeCfgSnmpTrapVersion, ipeCfgSnmpTrapNotifyType,
            ipeCfgSnmpTrapTargetAddress, ipeCfgSnmpTrapTargetV6Address,
            ipeCfgSnmpTrapTargetAddressType(*), ipeCfgSnmpTrapTaergetPort,
            ipeCfgSnmpTrapSecurityName
            ipeCfgSnmpTrapRowStatus     # Only createAndGo(4).
            
            Other object is not necessary. Even if it is done SET, it is
            checked the value, but ignored.
            
            1.3) SNMPv3 (ipeCfgSnmpTrapNotifyType = inform(2))
            To create a new row, you must SET objects indicated below.
            
            ipeCfgSnmpTrapVersion, ipeCfgSnmpTrapNotifyType,
            ipeCfgSnmpTrapTargetAddress, ipeCfgSnmpTrapTargetV6Address,
            ipeCfgSnmpTrapTargetAddressType(*), ipeCfgSnmpTrapTaergetPort,
            ipeCfgSnmpTrapSecurityName, ipeCfgSnmpTrapSecurityLevel,
            ipeCfgSnmpTrapEngineId, ipeCfgSnmpTrapAuthAlgorithm,
            ipeCfgSnmpTrapAuthKey, ipeCfgSnmpTrapPrivAlgorithm,
            ipeCfgSnmpTrapPrivKey
            ipeCfgSnmpTrapRowStatus    # Only createAndGo(4).
            
            * NOT for EX CPRI
            
            ipeCfgSnmpTrapEntryIndex is an index of this entry.
            
            2) how to destroy
            To destroy a exist row, you must SET a destory(6) to
            ipeCfgSnmpCommunityRowStatus.
            
            3) how to modify
            It is not possible.
            Please destroy a exist row, and create a new row."
        ::= { ipeCfgSnmpTrapEntry 14 }

    ipeCfgSnmpTrapTargetV6Address OBJECT-TYPE
        SYNTAX       Ipv6Address
        MAX-ACCESS   read-create
        STATUS       current
        DESCRIPTION  
            "Destination IPv6 address of this entry's notification.
                The following are not valid addresses:
                    ::1/128 IPv6 Loopback
                    ::/128 Unspecified
                    FF00::/8 IPv6 Multicasts"
        ::= { ipeCfgSnmpTrapEntry 15 }

    ipeCfgSnmpTrapTargetIfIndex OBJECT-TYPE
        SYNTAX       INTEGER {
                         invalid(0),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "The interface index through which the Server is reachable.
            When ipeCfgSnmpTrapTargetV6Address is configured with 
            Link-local address, this object must be configured
            to proper Interface index. For any other address type,
            value of this object shall be 0."
        ::= { ipeCfgSnmpTrapEntry 16 }

    ipeCfgSnmpTrapTargetAddressType OBJECT-TYPE
        SYNTAX       INTEGER { invalid(0), ipv4(1), ipv6(2) }
        MAX-ACCESS   read-create
        STATUS       current
        DESCRIPTION  
            "Indicate IP address type of this trap target.
            
            ipv4 : trap target address has IPv4 address.
            ipv6 : trap target address has IPv6 address.
            When this object is not specified at the object creation with the
            index 4 through 6, 'ipv4' is as the default."
        ::= { ipeCfgSnmpTrapEntry 17 }

    ipeCfgAccount OBJECT IDENTIFIER
        ::= { ipeConfigurationGroup 12 }

    ipeCfgAccountUserInfoTable OBJECT-TYPE
        SYNTAX       SEQUENCE OF IpeCfgAccountUserInfoEntry
        MAX-ACCESS   not-accessible
        STATUS       current
        DESCRIPTION  "Table of user Information."
        ::= { ipeCfgAccount 1 }

    ipeCfgAccountUserInfoEntry OBJECT-TYPE
        SYNTAX       IpeCfgAccountUserInfoEntry
        MAX-ACCESS   not-accessible
        STATUS       current
        DESCRIPTION  "Entry of user information."
        INDEX        { ipeCfgAccountUserIndex }
        ::= { ipeCfgAccountUserInfoTable 1 }

    IpeCfgAccountUserInfoEntry ::= SEQUENCE {
        ipeCfgAccountUserIndex                Integer32,
        ipeCfgAccountUserNEAddress            IpAddress,
        ipeCfgAccountUserName                 DisplayString,
        ipeCfgAccountUserKey                  DisplayString,
        ipeCfgAccountUserGroup                DisplayString,
        ipeCfgAccountUserSnmpV3SecurityLevel  INTEGER,
        ipeCfgAccountUserSnmpV3AuthAlgorithm  INTEGER,
        ipeCfgAccountUserSnmpV3AuthKey        DisplayString,
        ipeCfgAccountUserSnmpV3PrivAlgorithm  INTEGER,
        ipeCfgAccountUserSnmpV3PrivKey        DisplayString,
        ipeCfgAccountUserRowStatus            RowStatus,
        ipeCfgAccountUserKeyConfirmation      DisplayString,
        ipeCfgAccountKeyLifetime              Integer32
    }

    ipeCfgAccountUserIndex OBJECT-TYPE
        SYNTAX       Integer32 (1..102)
        MAX-ACCESS   not-accessible
        STATUS       current
        DESCRIPTION  "Index of table."
        ::= { ipeCfgAccountUserInfoEntry 1 }

    ipeCfgAccountUserNEAddress OBJECT-TYPE
        SYNTAX       IpAddress
        MAX-ACCESS   not-accessible
        STATUS       current
        DESCRIPTION  ""
        ::= { ipeCfgAccountUserInfoEntry 2 }

    ipeCfgAccountUserName OBJECT-TYPE
        SYNTAX       DisplayString (SIZE(1..31))
        MAX-ACCESS   read-create
        STATUS       current
        DESCRIPTION  
            "User Name.
            An overlap of a user name isn't permitted.
            
            Please use ASCII code."
        ::= { ipeCfgAccountUserInfoEntry 3 }

    ipeCfgAccountUserKey OBJECT-TYPE
        SYNTAX       DisplayString (SIZE(8..128))
        MAX-ACCESS   read-create
        STATUS       current
        DESCRIPTION  
            "User password. 
            This object can be operated only when in secure way."
        ::= { ipeCfgAccountUserInfoEntry 4 }

    ipeCfgAccountUserGroup OBJECT-TYPE
        SYNTAX       DisplayString (SIZE(1..31))
        MAX-ACCESS   read-create
        STATUS       current
        DESCRIPTION  "This object defines the privilege for the user."
        ::= { ipeCfgAccountUserInfoEntry 5 }

    ipeCfgAccountUserSnmpV3SecurityLevel OBJECT-TYPE
        SYNTAX       INTEGER {
                         invalid(0),
                         noAuthNoPriv(1),
                         authNoPriv(2),
                         authPriv(3)
                     }
        MAX-ACCESS   read-create
        STATUS       current
        DESCRIPTION  
            "SNMPv3 security level.
            
            Setting for SET/GET/TRAP at the time of the SNMPv3 use(INFORM is
            inapplicable)"
        ::= { ipeCfgAccountUserInfoEntry 6 }

    ipeCfgAccountUserSnmpV3AuthAlgorithm OBJECT-TYPE
        SYNTAX       INTEGER { invalid(0), md5(1), sha(2) }
        MAX-ACCESS   read-create
        STATUS       current
        DESCRIPTION  
            "Hash calculate algorithm of authenticate password.
            
            Setting for SET/GET/TRAP at the time of the SNMPv3 use(INFORM is
            inapplicable)"
        ::= { ipeCfgAccountUserInfoEntry 7 }

    ipeCfgAccountUserSnmpV3AuthKey OBJECT-TYPE
        SYNTAX       DisplayString (SIZE(8..128))
        MAX-ACCESS   read-create
        STATUS       current
        DESCRIPTION  
            "Authenticate password for SNMP SET/GET/TRAP PDU.
            This object can be operated only when in secure way. When the
            object 'ipeCfgSnmpTrapNotifyType' is set to inform(2), the INFORM
            PDU Authenticate key is configured by 'ipeCfgSnmpTrapAuthKey'."
        ::= { ipeCfgAccountUserInfoEntry 8 }

    ipeCfgAccountUserSnmpV3PrivAlgorithm OBJECT-TYPE
        SYNTAX       INTEGER { invalid(0), des(1), aes(2) }
        MAX-ACCESS   read-create
        STATUS       current
        DESCRIPTION  
            "Cipher algorithm.
            
            Setting for SET/GET/TRAP at the time of the SNMPv3 use(INFORM is
            inapplicable)"
        ::= { ipeCfgAccountUserInfoEntry 9 }

    ipeCfgAccountUserSnmpV3PrivKey OBJECT-TYPE
        SYNTAX       DisplayString (SIZE(8..128))
        MAX-ACCESS   read-create
        STATUS       current
        DESCRIPTION  
            "Privacy password for SNMP SET/GET/TRAP PDU.
            This object can be operated only when in secure way. When the
            'ipeCfgSnmpTrapNotifyType' is set to inform(2), the INFORM PDU
            Authenticate key is configured by 'ipeCfgSnmpTrapAuthKey'."
        ::= { ipeCfgAccountUserInfoEntry 10 }

    ipeCfgAccountUserRowStatus OBJECT-TYPE
        SYNTAX       RowStatus { active(1), createAndGo(4), destroy(6) }
        MAX-ACCESS   read-create
        STATUS       current
        DESCRIPTION  
            "This RowStatus has a status only active(1). 
            
            1) creating a entry
            When you make a new entry, you must SET objects indicated below.
            
            ipeCfgAccountUserIndex
            ipeCfgAccountUserName
            ipeCfgAccountUserKey
            ipeCfgAccountUserGroup
            ipeCfgAccountUserSnmpV3SecurityLevel
            ipeCfgAccountUserSnmpV3AuthAlgorithm
            ipeCfgAccountUserSnmpV3AuthKey
            ipeCfgAccountUserSnmpV3PrivAlgorithm
            ipeCfgAccountUserSnmpV3PrivKey
            ipeCfgAccountUserRowStatus <- createAndGo(4)
            
            2) modifing a entry
            ipeCfgAccountUserKey can only be changed.
            Other items can not be updated. Please do destroy of entry and a
            create.
            
            3) deleting a entry
            When you SET a destroy(6) to ipeCfgAccountUserRowStatus, the
            entry is destroyed.
            
            4) About SNMPv3
            When there is not ipeCfgAccountGroupInfoEntry corresponding to
            ipeCfgAccountUserGroup, SNMPv3-TRAP which I used
            ipeCfgAccountUserName for is output, but cannot use
            SNMPv3-Set/Get-Request."
        ::= { ipeCfgAccountUserInfoEntry 11 }

    ipeCfgAccountUserKeyConfirmation OBJECT-TYPE
        SYNTAX       DisplayString (SIZE(8..128))
        MAX-ACCESS   read-create
        STATUS       current
        DESCRIPTION  
            "This object can be operated in secure way.Confirmation of a used
            password. Acceptable characters for this object is shown below.
            '-', '_','0'-'9', 'a'-'z' and 'A'-'Z'. Even if GET is requested,
            this object returns a blank."
        ::= { ipeCfgAccountUserInfoEntry 12 }

    ipeCfgAccountKeyLifetime OBJECT-TYPE
        SYNTAX       Integer32 (0..180)
        UNITS        "days"
        MAX-ACCESS   read-create
        STATUS       current
        DESCRIPTION  "0 is unlimited."
        DEFVAL       { 90 }
        ::= { ipeCfgAccountUserInfoEntry 13 }

    ipeCfgAccountGroupInfoTable OBJECT-TYPE
        SYNTAX       SEQUENCE OF IpeCfgAccountGroupInfoEntry
        MAX-ACCESS   not-accessible
        STATUS       current
        DESCRIPTION  "Table of Group Information."
        ::= { ipeCfgAccount 2 }

    ipeCfgAccountGroupInfoEntry OBJECT-TYPE
        SYNTAX       IpeCfgAccountGroupInfoEntry
        MAX-ACCESS   not-accessible
        STATUS       current
        DESCRIPTION  "Entry of Group Information."
        INDEX        { ipeCfgAccountGroupIndex }
        ::= { ipeCfgAccountGroupInfoTable 1 }

    IpeCfgAccountGroupInfoEntry ::= SEQUENCE {
        ipeCfgAccountGroupIndex        Integer32,
        ipeCfgAccountGroupNEAddress    IpAddress,
        ipeCfgAccountGroupName         DisplayString,
        ipeCfgAccountGroupTelnet       INTEGER,
        ipeCfgAccountGroupSsh          INTEGER,
        ipeCfgAccountGroupFtp          INTEGER,
        ipeCfgAccountGroupSftp         INTEGER,
        ipeCfgAccountGroupHttp         INTEGER,
        ipeCfgAccountGroupHttps        INTEGER,
        ipeCfgAccountGroupSnmp         INTEGER,
        ipeCfgAccountGroupAccessLevel  INTEGER,
        ipeCfgAccountGroupRowStatus    RowStatus
    }

    ipeCfgAccountGroupIndex OBJECT-TYPE
        SYNTAX       Integer32 (1..10)
        MAX-ACCESS   not-accessible
        STATUS       current
        DESCRIPTION  "Index of table."
        ::= { ipeCfgAccountGroupInfoEntry 1 }

    ipeCfgAccountGroupNEAddress OBJECT-TYPE
        SYNTAX       IpAddress
        MAX-ACCESS   not-accessible
        STATUS       current
        DESCRIPTION  ""
        ::= { ipeCfgAccountGroupInfoEntry 2 }

    ipeCfgAccountGroupName OBJECT-TYPE
        SYNTAX       DisplayString (SIZE(1..31))
        MAX-ACCESS   read-create
        STATUS       current
        DESCRIPTION  
            "Group name.
            An overlap of a group name isn't permitted.
            
            Please use ASCII code.
            
            The characters which can be used are '-', '_','0'-'9', 'a'-'z'
            and 'A'-'Z'."
        ::= { ipeCfgAccountGroupInfoEntry 3 }

    ipeCfgAccountGroupTelnet OBJECT-TYPE
        SYNTAX       INTEGER { invalid(0), disabled(1), enabled(2) }
        MAX-ACCESS   read-create
        STATUS       current
        DESCRIPTION  "TELNET enable."
        ::= { ipeCfgAccountGroupInfoEntry 4 }

    ipeCfgAccountGroupSsh OBJECT-TYPE
        SYNTAX       INTEGER { invalid(0), disabled(1), enabled(2) }
        MAX-ACCESS   read-create
        STATUS       current
        DESCRIPTION  "SSH enable."
        ::= { ipeCfgAccountGroupInfoEntry 5 }

    ipeCfgAccountGroupFtp OBJECT-TYPE
        SYNTAX       INTEGER { invalid(0), disabled(1), enabled(2) }
        MAX-ACCESS   read-create
        STATUS       current
        DESCRIPTION  "FTP enable."
        ::= { ipeCfgAccountGroupInfoEntry 6 }

    ipeCfgAccountGroupSftp OBJECT-TYPE
        SYNTAX       INTEGER { invalid(0), disabled(1), enabled(2) }
        MAX-ACCESS   read-create
        STATUS       current
        DESCRIPTION  "SFTP enable."
        ::= { ipeCfgAccountGroupInfoEntry 7 }

    ipeCfgAccountGroupHttp OBJECT-TYPE
        SYNTAX       INTEGER { invalid(0), disabled(1), enabled(2) }
        MAX-ACCESS   read-create
        STATUS       current
        DESCRIPTION  "HTTP enable."
        ::= { ipeCfgAccountGroupInfoEntry 8 }

    ipeCfgAccountGroupHttps OBJECT-TYPE
        SYNTAX       INTEGER { invalid(0), disabled(1), enabled(2) }
        MAX-ACCESS   read-create
        STATUS       current
        DESCRIPTION  "HTTPS enable."
        ::= { ipeCfgAccountGroupInfoEntry 9 }

    ipeCfgAccountGroupSnmp OBJECT-TYPE
        SYNTAX       INTEGER { invalid(0), disabled(1), enabled(2) }
        MAX-ACCESS   read-create
        STATUS       current
        DESCRIPTION  "SNMP enable."
        ::= { ipeCfgAccountGroupInfoEntry 10 }

    ipeCfgAccountGroupAccessLevel OBJECT-TYPE
        SYNTAX       INTEGER {
                         invalid(0),
                         operatorLevel(1),
                         configLevel(2),
                         adminLevel(3),
                         debugLevel(4)
                     }
        MAX-ACCESS   read-create
        STATUS       current
        DESCRIPTION  "Access level."
        ::= { ipeCfgAccountGroupInfoEntry 11 }

    ipeCfgAccountGroupRowStatus OBJECT-TYPE
        SYNTAX       RowStatus { active(1), createAndGo(4), destroy(6) }
        MAX-ACCESS   read-create
        STATUS       current
        DESCRIPTION  
            "This RowStatus has a status only 'active(1)'. 
            
            1) creating a entry.
            When you make a new entry, you must SET objects indicated below.
            
            ipeCfgAccountGroupName
            ipeCfgAccountGroupTelnet
            ipeCfgAccountGroupSsh
            ipeCfgAccountGroupFtp
            ipeCfgAccountGroupSftp
            ipeCfgAccountGroupHttp
            ipeCfgAccountGroupHttps
            ipeCfgAccountGroupSnmp
            ipeCfgAccountGroupAccessLevel
            ipeCfgAccountGroupRowStatus <- createAndGo(4)
            
            ipeCfgAccountGroupIndex is an index of this entry.
            
            2) deleting a entry.
            When you SET a destroy(6) to ipeCfgAccountGroupRowStatus, the
            entry is destroyed.
            
            Information that synchronizes and is deleted:
             User Information setting(ssh/ftp/http login information)
             SNMPv3-Set/Get-Req user info
            (The SNMPv3-TRAP information is left)
            
            3) modifing a entry
            It can change it other than ipeCfgAccountGroupName,
            ipeCfgAccountGroupRowStatus. But the 'ipeCfgAccountGroupName' of
            predefined groups cannot be changed."
        ::= { ipeCfgAccountGroupInfoEntry 12 }

    ipeCfgUserAccountAuthTable OBJECT-TYPE
        SYNTAX       SEQUENCE OF IpeCfgUserAccountAuthEntry
        MAX-ACCESS   not-accessible
        STATUS       current
        DESCRIPTION  "Configure user authentication method about Web LCT."
        ::= { ipeCfgAccount 4 }

    ipeCfgUserAccountAuthEntry OBJECT-TYPE
        SYNTAX       IpeCfgUserAccountAuthEntry
        MAX-ACCESS   not-accessible
        STATUS       current
        DESCRIPTION  "..."
        INDEX        { ipeCfgUserAccountAuthIndex }
        ::= { ipeCfgUserAccountAuthTable 1 }

    IpeCfgUserAccountAuthEntry ::= SEQUENCE {
        ipeCfgUserAccountAuthIndex          Integer32,
        ipeCfgUserAccountAuthNEAddress      IpAddress,
        ipeCfgUserAccountAuthMode           INTEGER,
        ipeCfgUserAccountAuthOrder          INTEGER,
        ipeCfgUserAccountAuthTrapEnable     INTEGER,
        ipeCfgUserAccountAuthTrapLocal      INTEGER,
        ipeCfgUserAccountAuthTrapExternal   INTEGER,
        ipeCfgUserAccountAuthProtection     EnableDisableValue,
        ipeCfgUserAccountAuthTotalNumber    Integer32,
        ipeCfgUserAcctAuthUserNameStrength  EnableDisableValue,
        ipeCfgUserAcctAuthPasswdStrength    EnableDisableValue,
        ipeCfgUserAcctAuthLoginAttempts     INTEGER,
        ipeCfgUserAcctAuthAutoLogout        EnableDisableValue,
        ipeCfgUserAcctAuthIdleTimeout       Integer32
    }

    ipeCfgUserAccountAuthIndex OBJECT-TYPE
        SYNTAX       Integer32 (1..1)
        MAX-ACCESS   not-accessible
        STATUS       current
        DESCRIPTION  "The index of this table."
        ::= { ipeCfgUserAccountAuthEntry 1 }

    ipeCfgUserAccountAuthNEAddress OBJECT-TYPE
        SYNTAX       IpAddress
        MAX-ACCESS   not-accessible
        STATUS       current
        DESCRIPTION  "Reserved object for northbound interface."
        ::= { ipeCfgUserAccountAuthEntry 2 }

    ipeCfgUserAccountAuthMode OBJECT-TYPE
        SYNTAX       INTEGER { invalid(0), mode1(1), mode2(2), mode3(3) }
        MAX-ACCESS   read-write
        STATUS       current
        DESCRIPTION  
            "Indicate the user authentication mode.
            
            mode1 : local authentication only.
            mode2 : local and LDAP authentication. (NOT SUPPORTED)
            mode3 : local and RADIUS authentication. 
            
            mode2 will be supprted in future version."
        DEFVAL       { mode1 }
        ::= { ipeCfgUserAccountAuthEntry 3 }

    ipeCfgUserAccountAuthOrder OBJECT-TYPE
        SYNTAX       INTEGER {
                         invalid(0),
                         localAuthFirst(1),
                         externalAuthFirst(2)
                     }
        MAX-ACCESS   read-write
        STATUS       current
        DESCRIPTION  
            "Indicate the user authentication order.
            This object is effective only if ipeCfgUserAccountAuthMode
            is set to mode2 or mode3.
            External authentication means authentication with RADIUS or
            LDAP.
            
            localAuthFirst    : local -> external
            externalAuthFirst : external -> local"
        DEFVAL       { localAuthFirst }
        ::= { ipeCfgUserAccountAuthEntry 4 }

    ipeCfgUserAccountAuthTrapEnable OBJECT-TYPE
        SYNTAX       INTEGER { invalid(0), disable(1), enable(2) }
        MAX-ACCESS   read-write
        STATUS       current
        DESCRIPTION  
            "Enable or disable user login trap.
            In case this object is set to enable, the system sends trap
            when user attempt to login to Web LCT."
        DEFVAL       { enable }
        ::= { ipeCfgUserAccountAuthEntry 5 }

    ipeCfgUserAccountAuthTrapLocal OBJECT-TYPE
        SYNTAX       INTEGER { invalid(0), success(1), failure(2) }
        MAX-ACCESS   read-only
        STATUS       current
        DESCRIPTION  
            "Indicate authentication result of local authentication.
            This object is dedicated for login control trap.
            If you read this object, the system returns invalid(0)."
        DEFVAL       { invalid }
        ::= { ipeCfgUserAccountAuthEntry 6 }

    ipeCfgUserAccountAuthTrapExternal OBJECT-TYPE
        SYNTAX       INTEGER { invalid(0), success(1), failure(2) }
        MAX-ACCESS   read-only
        STATUS       current
        DESCRIPTION  
            "Indicate authentication result of externel authentication.
            This object is dedicated for login control trap.
            If you read this object, the system returns invalid(0)."
        DEFVAL       { invalid }
        ::= { ipeCfgUserAccountAuthEntry 7 }

    ipeCfgUserAccountAuthProtection OBJECT-TYPE
        SYNTAX       EnableDisableValue
        MAX-ACCESS   read-write
        STATUS       current
        DESCRIPTION  "Indicates whether login protection is enabled."
        ::= { ipeCfgUserAccountAuthEntry 8 }

    ipeCfgUserAccountAuthTotalNumber OBJECT-TYPE
        SYNTAX       Integer32 (1..10)
        MAX-ACCESS   read-write
        STATUS       current
        DESCRIPTION  
            "The maximum sessions of users belong to the predefined groups
            which have configuration privilege."
        DEFVAL       { 5 }
        ::= { ipeCfgUserAccountAuthEntry 9 }

    ipeCfgUserAcctAuthUserNameStrength OBJECT-TYPE
        SYNTAX       EnableDisableValue
        MAX-ACCESS   read-write
        STATUS       current
        DESCRIPTION  
            "Indicates User Name Strength Enforcement for LCT only."
        ::= { ipeCfgUserAccountAuthEntry 10 }

    ipeCfgUserAcctAuthPasswdStrength OBJECT-TYPE
        SYNTAX       EnableDisableValue
        MAX-ACCESS   read-write
        STATUS       current
        DESCRIPTION  
            "Indicates Password Strength Enforcement for LCT only."
        ::= { ipeCfgUserAccountAuthEntry 11 }

    ipeCfgUserAcctAuthLoginAttempts OBJECT-TYPE
        SYNTAX       INTEGER {
                         invalid(0),
                         protectIn3Attempts(3),
                         protectIn5Attempts(5)
                     }
        MAX-ACCESS   read-write
        STATUS       current
        DESCRIPTION  
            "Indicates the number of Unsuccessful Login Attempts for the
            login protection.
            When changing this setting the ipeStsAccountUserStatus for all
            accounts indicates 'normal' forcibly based on the state
            transition."
        ::= { ipeCfgUserAccountAuthEntry 12 }

    ipeCfgUserAcctAuthAutoLogout OBJECT-TYPE
        SYNTAX       EnableDisableValue
        MAX-ACCESS   read-write
        STATUS       current
        DESCRIPTION  "Indicates Auto-Logout for LCT only."
        ::= { ipeCfgUserAccountAuthEntry 13 }

    ipeCfgUserAcctAuthIdleTimeout OBJECT-TYPE
        SYNTAX       Integer32 (1..1440)
        UNITS        "minutes"
        MAX-ACCESS   read-write
        STATUS       current
        DESCRIPTION  "	IndicatesAutologoutTime value."
        DEFVAL       { 30 }
        ::= { ipeCfgUserAccountAuthEntry 14 }

    ipeCfgDhcpGroup OBJECT IDENTIFIER
        ::= { ipeConfigurationGroup 13 }

    ipeCfgDhcpServerTable OBJECT-TYPE
        SYNTAX       SEQUENCE OF IpeCfgDhcpServerEntry
        MAX-ACCESS   not-accessible
        STATUS       current
        DESCRIPTION  "DHCPserver table."
        ::= { ipeCfgDhcpGroup 1 }

    ipeCfgDhcpServerEntry OBJECT-TYPE
        SYNTAX       IpeCfgDhcpServerEntry
        MAX-ACCESS   not-accessible
        STATUS       current
        DESCRIPTION  "entry of DHCPserver table."
        INDEX        { ipeCfgDhcpServerIndex }
        ::= { ipeCfgDhcpServerTable 1 }

    IpeCfgDhcpServerEntry ::= SEQUENCE {
        ipeCfgDhcpServerIndex          Integer32,
        ipeCfgDhcpServerNEAddress      IpAddress,
        ipeCfgDhcpServerEnable         INTEGER,
        ipeCfgDhcpLeaseAddrRangeBegin  IpAddress,
        ipeCfgDhcpLeaseAddrRangeEnd    IpAddress
    }

    ipeCfgDhcpServerIndex OBJECT-TYPE
        SYNTAX       Integer32 (1..2)
        MAX-ACCESS   not-accessible
        STATUS       current
        DESCRIPTION  
            "Index of this table.
            Index value '2' is used for redundant Ctrl card."
        ::= { ipeCfgDhcpServerEntry 1 }

    ipeCfgDhcpServerNEAddress OBJECT-TYPE
        SYNTAX       IpAddress
        MAX-ACCESS   not-accessible
        STATUS       current
        DESCRIPTION  ""
        ::= { ipeCfgDhcpServerEntry 2 }

    ipeCfgDhcpServerEnable OBJECT-TYPE
        SYNTAX       INTEGER { start(1), stop(2), restart(3) }
        MAX-ACCESS   read-write
        STATUS       current
        DESCRIPTION  
            "Effective/invalid setting of DHCP.
            value range:start(1)
                        stop(2)
                        restart(3)
            DHCPD has already started. When the start is specified, DHCPD
            restart."
        ::= { ipeCfgDhcpServerEntry 3 }

    ipeCfgDhcpLeaseAddrRangeBegin OBJECT-TYPE
        SYNTAX       IpAddress
        MAX-ACCESS   read-write
        STATUS       current
        DESCRIPTION  
            "Beginning IPaddress within the range of lease address.
            value range:Dotted decimal notation
            denial value:0.0.0.0 , 127.0.0.1 , 255.255.255.255
            ipeCfgDhcpLeaseAddrRangeBegin don't same as
            ipeCfgPortLctIpAddress value"
        ::= { ipeCfgDhcpServerEntry 4 }

    ipeCfgDhcpLeaseAddrRangeEnd OBJECT-TYPE
        SYNTAX       IpAddress
        MAX-ACCESS   read-write
        STATUS       current
        DESCRIPTION  
            "End IPaddress within the range of lease address.
            value range:Dotted decimal notation
            denial value:0.0.0.0 , 127.0.0.1 , 255.255.255.255
            ipeCfgDhcpLeaseAddrRangeEnd don't same as ipeCfgPortLctIpAddress
            value"
        ::= { ipeCfgDhcpServerEntry 5 }

    ipeCfgStpGroup OBJECT IDENTIFIER
        ::= { ipeConfigurationGroup 14 }

    ipeCfgStpBridgeTable OBJECT-TYPE
        SYNTAX       SEQUENCE OF IpeCfgStpBridgeEntry
        MAX-ACCESS   not-accessible
        STATUS       current
        DESCRIPTION  "STP state setting table."
        ::= { ipeCfgStpGroup 1 }

    ipeCfgStpBridgeEntry OBJECT-TYPE
        SYNTAX       IpeCfgStpBridgeEntry
        MAX-ACCESS   not-accessible
        STATUS       current
        DESCRIPTION  "entry of STP state setting table."
        INDEX        { ipeCfgStpBridgeIndex }
        ::= { ipeCfgStpBridgeTable 1 }

    IpeCfgStpBridgeEntry ::= SEQUENCE {
        ipeCfgStpBridgeIndex         Integer32,
        ipeCfgStpBridgeNEAddress     IpAddress,
        ipeCfgStpEnable              INTEGER,
        ipeCfgStpPriority            Integer32,
        ipeCfgStpBridgeMaxAge        Timeout,
        ipeCfgStpBridgeHelloTime     Timeout,
        ipeCfgStpBridgeForwardDelay  Timeout,
        ipeCfgStpBridgeAutoEnable    OffOnValue
    }

    ipeCfgStpBridgeIndex OBJECT-TYPE
        SYNTAX       Integer32 (1..20)
        MAX-ACCESS   not-accessible
        STATUS       current
        DESCRIPTION  
            "Index of this ipeCfgStpBridgeEntry.
            Range from 1 o 20."
        ::= { ipeCfgStpBridgeEntry 1 }

    ipeCfgStpBridgeNEAddress OBJECT-TYPE
        SYNTAX       IpAddress
        MAX-ACCESS   not-accessible
        STATUS       current
        DESCRIPTION  ""
        ::= { ipeCfgStpBridgeEntry 2 }

    ipeCfgStpEnable OBJECT-TYPE
        SYNTAX       INTEGER { enabled(1), disabled(2) }
        MAX-ACCESS   read-write
        STATUS       current
        DESCRIPTION  
            "Effective/invalid setting of STP.
            value :enabled
                   disabled"
        ::= { ipeCfgStpBridgeEntry 3 }

    ipeCfgStpPriority OBJECT-TYPE
        SYNTAX       Integer32 (0..65535)
        MAX-ACCESS   read-write
        STATUS       current
        DESCRIPTION  
            "Bridge priority.
            value range:0 to 65535"
        ::= { ipeCfgStpBridgeEntry 4 }

    ipeCfgStpBridgeMaxAge OBJECT-TYPE
        SYNTAX       Timeout (600..4000)
        MAX-ACCESS   read-write
        STATUS       current
        DESCRIPTION  
            "MaxAge (in units of hundredths of a second).
            value range:600 to 4000
            rule: 2 * (ipeCfgStpBridgeForwardDelay - 1) =>
            ipeCfgStpBridgeMaxAge
                 ipeCfgStpBridgeMaxAge >= 2 * (ipeCfgStpBridgeHelloTime + 1)"
        ::= { ipeCfgStpBridgeEntry 5 }

    ipeCfgStpBridgeHelloTime OBJECT-TYPE
        SYNTAX       Timeout (100..1000)
        MAX-ACCESS   read-write
        STATUS       current
        DESCRIPTION  
            "HelloTime (in units of hundredths of a second).
            value range:100 to 1000
            rule:ipeCfgStpBridgeMaxAge >= 2x(ipeCfgStpBridgeHelloTime + 1)"
        ::= { ipeCfgStpBridgeEntry 6 }

    ipeCfgStpBridgeForwardDelay OBJECT-TYPE
        SYNTAX       Timeout (400..3000)
        MAX-ACCESS   read-write
        STATUS       current
        DESCRIPTION  
            "ForwardDelay (in units of hundredths of a second).
            value range:400 to 3000
            rule: 2 * (ipeCfgStpBridgeForwardDelay - 1) >=
            ipeCfgStpBridgeMaxAge"
        ::= { ipeCfgStpBridgeEntry 7 }

    ipeCfgStpBridgeAutoEnable OBJECT-TYPE
        SYNTAX       OffOnValue
        MAX-ACCESS   read-write
        STATUS       current
        DESCRIPTION  
            "This object configures automatic enabling M-plane STP.
            When the automatic enabling is configured, 'ipeCfgStpEnable' does
            not control STP function, STP function will be enabled by the
            system automatically."
        ::= { ipeCfgStpBridgeEntry 8 }

    ipeCfgStpPortTable OBJECT-TYPE
        SYNTAX       SEQUENCE OF IpeCfgStpPortEntry
        MAX-ACCESS   not-accessible
        STATUS       current
        DESCRIPTION  "STP port information table."
        ::= { ipeCfgStpGroup 2 }

    ipeCfgStpPortEntry OBJECT-TYPE
        SYNTAX       IpeCfgStpPortEntry
        MAX-ACCESS   not-accessible
        STATUS       current
        DESCRIPTION  "entry of  STP port information table."
        INDEX        { ipeCfgStpPortIfIndex }
        ::= { ipeCfgStpPortTable 1 }

    IpeCfgStpPortEntry ::= SEQUENCE {
        ipeCfgStpPortIfIndex     InterfaceIndex,
        ipeCfgStpPortNEAddress   IpAddress,
        ipeCfgStpPortPriority    Integer32,
        ipeCfgStpPortPathCost    Integer32,
        ipeCfgStpPortEdgeEnable  INTEGER
    }

    ipeCfgStpPortIfIndex OBJECT-TYPE
        SYNTAX       InterfaceIndex
        MAX-ACCESS   not-accessible
        STATUS       current
        DESCRIPTION  "Index of I/F table."
        ::= { ipeCfgStpPortEntry 1 }

    ipeCfgStpPortNEAddress OBJECT-TYPE
        SYNTAX       IpAddress
        MAX-ACCESS   not-accessible
        STATUS       current
        DESCRIPTION  ""
        ::= { ipeCfgStpPortEntry 2 }

    ipeCfgStpPortPriority OBJECT-TYPE
        SYNTAX       Integer32 (0..63)
        MAX-ACCESS   read-write
        STATUS       current
        DESCRIPTION  
            "Port priority.
            value range:0 to 63"
        ::= { ipeCfgStpPortEntry 3 }

    ipeCfgStpPortPathCost OBJECT-TYPE
        SYNTAX       Integer32 (1..65535)
        MAX-ACCESS   read-write
        STATUS       current
        DESCRIPTION  
            "Pathcost.
            value range:1 to 65535"
        ::= { ipeCfgStpPortEntry 4 }

    ipeCfgStpPortEdgeEnable OBJECT-TYPE
        SYNTAX       INTEGER { enabled(1), disabled(2) }
        MAX-ACCESS   read-write
        STATUS       current
        DESCRIPTION  
            "Effective/invalid setting of BPDU.
            value range:enabled(1)
                        disabled(2)"
        ::= { ipeCfgStpPortEntry 5 }

    ipeCfgPortGroup OBJECT IDENTIFIER
        ::= { ipeConfigurationGroup 15 }

    ipeCfgPortModemTable OBJECT-TYPE
        SYNTAX       SEQUENCE OF IpeCfgPortModemEntry
        MAX-ACCESS   not-accessible
        STATUS       current
        DESCRIPTION  "MODEM port set up information table."
        ::= { ipeCfgPortGroup 1 }

    ipeCfgPortModemEntry OBJECT-TYPE
        SYNTAX       IpeCfgPortModemEntry
        MAX-ACCESS   not-accessible
        STATUS       current
        DESCRIPTION  "entry of  MODEM port set up information table."
        INDEX        { ipeCfgPortModemIfIndex }
        ::= { ipeCfgPortModemTable 1 }

    IpeCfgPortModemEntry ::= SEQUENCE {
        ipeCfgPortModemIfIndex    InterfaceIndex,
        ipeCfgPortModemNEAddress  IpAddress,
        ipeCfgPortModemEnable     INTEGER
    }

    ipeCfgPortModemIfIndex OBJECT-TYPE
        SYNTAX       InterfaceIndex
        MAX-ACCESS   not-accessible
        STATUS       current
        DESCRIPTION  "Index of table."
        ::= { ipeCfgPortModemEntry 1 }

    ipeCfgPortModemNEAddress OBJECT-TYPE
        SYNTAX       IpAddress
        MAX-ACCESS   not-accessible
        STATUS       current
        DESCRIPTION  ""
        ::= { ipeCfgPortModemEntry 2 }

    ipeCfgPortModemEnable OBJECT-TYPE
        SYNTAX       INTEGER { enabled(1), disabled(2) }
        MAX-ACCESS   read-write
        STATUS       current
        DESCRIPTION  
            "Effective/invalid setting of MODEM port.
            value range: enabled(1)
                        disabled(2)"
        ::= { ipeCfgPortModemEntry 3 }

    ipeCfgPortEtherTable OBJECT-TYPE
        SYNTAX       SEQUENCE OF IpeCfgPortEtherEntry
        MAX-ACCESS   not-accessible
        STATUS       current
        DESCRIPTION  "NMS/NE1 port set up information table."
        ::= { ipeCfgPortGroup 3 }

    ipeCfgPortEtherEntry OBJECT-TYPE
        SYNTAX       IpeCfgPortEtherEntry
        MAX-ACCESS   not-accessible
        STATUS       current
        DESCRIPTION  "entry of  NMS/NE1 port set up information table."
        INDEX        { ipeCfgPortEtherIfIndex }
        ::= { ipeCfgPortEtherTable 1 }

    IpeCfgPortEtherEntry ::= SEQUENCE {
        ipeCfgPortEtherIfIndex            InterfaceIndex,
        ipeCfgPortEtherNEAddress          IpAddress,
        ipeCfgPortEtherEnable             INTEGER,
        ipeCfgPortEtherAutoNeg            INTEGER,
        ipeCfgPortEtherSpecialFilter      INTEGER,
        ipeCfgPortEtherLldpMode           INTEGER,
        ipeCfgPortEtherVlanPortType       INTEGER,
        ipeCfgPortEtherLldpPortIdSubtype  INTEGER
    }

    ipeCfgPortEtherIfIndex OBJECT-TYPE
        SYNTAX       InterfaceIndex
        MAX-ACCESS   not-accessible
        STATUS       current
        DESCRIPTION  "Index of table."
        ::= { ipeCfgPortEtherEntry 1 }

    ipeCfgPortEtherNEAddress OBJECT-TYPE
        SYNTAX       IpAddress
        MAX-ACCESS   not-accessible
        STATUS       current
        DESCRIPTION  ""
        ::= { ipeCfgPortEtherEntry 2 }

    ipeCfgPortEtherEnable OBJECT-TYPE
        SYNTAX       INTEGER { enabled(1), disabled(2) }
        MAX-ACCESS   read-write
        STATUS       current
        DESCRIPTION  
            "Effective/invalid setting of NMS/NE1 port.
            value range: enabled(1)
                        disabled(2)
            default value is 'enabled'.(iPASOLINK EX Advanced)"
        DEFVAL       { enabled }
        ::= { ipeCfgPortEtherEntry 3 }

    ipeCfgPortEtherAutoNeg OBJECT-TYPE
        SYNTAX       INTEGER { enabled(1), disabled(2) }
        MAX-ACCESS   read-write
        STATUS       current
        DESCRIPTION  
            "Auto negotiation invalid effective/setting of NMS/NE1 port.
            value range: enabled(1)
                        disabled(2)"
        ::= { ipeCfgPortEtherEntry 4 }

    ipeCfgPortEtherSpecialFilter OBJECT-TYPE
        SYNTAX       INTEGER { true(1), false(2) }
        MAX-ACCESS   read-write
        STATUS       current
        DESCRIPTION  
            "Setting of whether a special broadcast packet is blocked."
        ::= { ipeCfgPortEtherEntry 5 }

    ipeCfgPortEtherLldpMode OBJECT-TYPE
        SYNTAX       INTEGER { invalid(0), standardMode(1), proprietaryMode(2) }
        MAX-ACCESS   read-write
        STATUS       current
        DESCRIPTION  
            "Switch to select MAC address of LLDP Frame.
            
              standardMode    : MAC address of LLDP Frame is 
                                01-80-C2-00-00-0E.
              proprietaryMode : MAC address of LLDP Frame is configured in 
                                ipeCfgLldpProprietaryModeMacAddress."
        DEFVAL       { standardMode }
        ::= { ipeCfgPortEtherEntry 6 }

    ipeCfgPortEtherVlanPortType OBJECT-TYPE
        SYNTAX       INTEGER { access(1), trunk(3) }
        MAX-ACCESS   read-write
        STATUS       current
        DESCRIPTION  
            "VLAN Port Type of NMS port.
            This value is not available (iPASOLINK EX Advanced)."
        ::= { ipeCfgPortEtherEntry 7 }

    ipeCfgPortEtherLldpPortIdSubtype OBJECT-TYPE
        SYNTAX       INTEGER { invalid(0), macAddress(3), interfaceName(5) }
        MAX-ACCESS   read-write
        STATUS       current
        DESCRIPTION  
            "Switch to select LLDP Port ID TLV Subtype of NMS/NE1 Port.
            
            macAddress (subtype 3)    : equipment send the ifIndex
            information using Port ID TLV.
            interfaceName (subtype 5) : equipment send the Port Name
            information using Port ID TLV."
        DEFVAL       { macAddress }
        ::= { ipeCfgPortEtherEntry 8 }

    ipeCfgPortInbandTable OBJECT-TYPE
        SYNTAX       SEQUENCE OF IpeCfgPortInbandEntry
        MAX-ACCESS   not-accessible
        STATUS       current
        DESCRIPTION  
            "InBand Management VLAN port set up information table."
        ::= { ipeCfgPortGroup 6 }

    ipeCfgPortInbandEntry OBJECT-TYPE
        SYNTAX       IpeCfgPortInbandEntry
        MAX-ACCESS   not-accessible
        STATUS       current
        DESCRIPTION  
            "entry of  INBAND Management VLAN port set up information table."
        INDEX        { ipeCfgPortInbandIfIndex }
        ::= { ipeCfgPortInbandTable 1 }

    IpeCfgPortInbandEntry ::= SEQUENCE {
        ipeCfgPortInbandIfIndex    InterfaceIndex,
        ipeCfgPortInbandNEAddress  IpAddress,
        ipeCfgPortInbandIpAddress  IpAddress,
        ipeCfgPortInbandNetMask    IpAddress,
        ipeCfgPortInbandEnable     INTEGER,
        ipeCfgPortInbandVlanId     Integer32,
        ipeCfgPortInbandMtu        Integer32,
        ipeCfgPortInbandCos        Integer32,
        ipeCfgPortInbandSVlanId    Integer32
    }

    ipeCfgPortInbandIfIndex OBJECT-TYPE
        SYNTAX       InterfaceIndex
        MAX-ACCESS   not-accessible
        STATUS       current
        DESCRIPTION  "Index of table."
        ::= { ipeCfgPortInbandEntry 1 }

    ipeCfgPortInbandNEAddress OBJECT-TYPE
        SYNTAX       IpAddress
        MAX-ACCESS   not-accessible
        STATUS       current
        DESCRIPTION  ""
        ::= { ipeCfgPortInbandEntry 2 }

    ipeCfgPortInbandIpAddress OBJECT-TYPE
        SYNTAX       IpAddress
        MAX-ACCESS   read-write
        STATUS       obsolete
        DESCRIPTION  
            "IPaddress of INBAND Management VLAN port.
            It makes an error of the Internet Protocol address setting that
            overlaps in the port in the device.
            The object port and the range of the value are described as
            follows.
            Object port: Lct, InbandMngVLAN1-16, Bridge1-20, NE2
            Value range: 0x00000000 - 0xdfffffff(0.0.0.0 - 223.255.255.255)
            The relation is not in the state and the number of Branch of
            interfaces and the Internet Protocol address repetition check is
            checked.
            
            When 0.0.0.0 is set to ipeCfgPortInbandIpAddress, it becomes an
            Internet Protocol address deletion."
        ::= { ipeCfgPortInbandEntry 3 }

    ipeCfgPortInbandNetMask OBJECT-TYPE
        SYNTAX       IpAddress
        MAX-ACCESS   read-write
        STATUS       obsolete
        DESCRIPTION  
            "Subnet mask of INBAND Management VLAN port.
            When it isn't proper as subnetmask, it'll be an error.
            Value range:0x00000000 - 0xfffffffc(0 - 30bit)"
        ::= { ipeCfgPortInbandEntry 4 }

    ipeCfgPortInbandEnable OBJECT-TYPE
        SYNTAX       INTEGER { enabled(1), disabled(2) }
        MAX-ACCESS   read-write
        STATUS       current
        DESCRIPTION  
            "Effective/invalid setting of INBAND Management VLAN port.
            value range: enabled(1)
                        disabled(2)"
        ::= { ipeCfgPortInbandEntry 5 }

    ipeCfgPortInbandVlanId OBJECT-TYPE
        SYNTAX       Integer32 (1..4094)
        MAX-ACCESS   read-write
        STATUS       current
        DESCRIPTION  
            "VLAN ID of INBAND Management VLAN port.
            value range:1 to 4094"
        ::= { ipeCfgPortInbandEntry 6 }

    ipeCfgPortInbandMtu OBJECT-TYPE
        SYNTAX       Integer32 (256..1500)
        MAX-ACCESS   read-write
        STATUS       obsolete
        DESCRIPTION  
            "MTU value of INBAND Management VLAN port.
            value range:256 to 1500"
        ::= { ipeCfgPortInbandEntry 7 }

    ipeCfgPortInbandCos OBJECT-TYPE
        SYNTAX       Integer32 (0..7)
        MAX-ACCESS   read-write
        STATUS       current
        DESCRIPTION  "CoS value of INBAND Management VLAN port"
        DEFVAL       { 7 }
        ::= { ipeCfgPortInbandEntry 8 }

    ipeCfgPortInbandSVlanId OBJECT-TYPE
        SYNTAX       Integer32 (1..4094)
        MAX-ACCESS   read-write
        STATUS       current
        DESCRIPTION  
            "Service VLAN ID of INBAND Management VLAN port.
            value range: 1 to 4094"
        ::= { ipeCfgPortInbandEntry 9 }

    ipeCfgPortMainEtherTable OBJECT-TYPE
        SYNTAX       SEQUENCE OF IpeCfgPortMainEtherEntry
        MAX-ACCESS   not-accessible
        STATUS       current
        DESCRIPTION  "Main traffic ether port set up information table."
        ::= { ipeCfgPortGroup 7 }

    ipeCfgPortMainEtherEntry OBJECT-TYPE
        SYNTAX       IpeCfgPortMainEtherEntry
        MAX-ACCESS   not-accessible
        STATUS       current
        DESCRIPTION  
            "entry of main traffic ether port set up information table."
        INDEX        { ipeCfgPortMainEtherIfIndex }
        ::= { ipeCfgPortMainEtherTable 1 }

    IpeCfgPortMainEtherEntry ::= SEQUENCE {
        ipeCfgPortMainEtherIfIndex            InterfaceIndex,
        ipeCfgPortMainEtherNEAddress          IpAddress,
        ipeCfgPortMainEtherLldpMode           INTEGER,
        ipeCfgPortMainEtherLldpPortIdSubtype  INTEGER
    }

    ipeCfgPortMainEtherIfIndex OBJECT-TYPE
        SYNTAX       InterfaceIndex
        MAX-ACCESS   not-accessible
        STATUS       current
        DESCRIPTION  
            "Index of table.
            Ifindex of main traffic ether port."
        ::= { ipeCfgPortMainEtherEntry 1 }

    ipeCfgPortMainEtherNEAddress OBJECT-TYPE
        SYNTAX       IpAddress
        MAX-ACCESS   not-accessible
        STATUS       current
        DESCRIPTION  "reserved."
        ::= { ipeCfgPortMainEtherEntry 2 }

    ipeCfgPortMainEtherLldpMode OBJECT-TYPE
        SYNTAX       INTEGER { invalid(0), standardMode(1), proprietaryMode(2) }
        MAX-ACCESS   read-write
        STATUS       current
        DESCRIPTION  
            "Switch to select MAC address of LLDP Frame.
                         
            standardMode    : MAC address of LLDP Frame is 01-80-C2-00-00-0E.
            proprietaryMode : MAC address of LLDP Frame is configured in 
                              ipeCfgLldpProprietaryModeMacAddress."
        DEFVAL       { standardMode }
        ::= { ipeCfgPortMainEtherEntry 3 }

    ipeCfgPortMainEtherLldpPortIdSubtype OBJECT-TYPE
        SYNTAX       INTEGER { invalid(0), macAddress(3), interfaceName(5) }
        MAX-ACCESS   read-write
        STATUS       current
        DESCRIPTION  
            "Switch to select LLDP Port ID TLV Subtype of User Port.
            
            macAddress (subtype 3)    : equipment send the ifIndex
            information using Port ID TLV.
            interfaceName (subtype 5) : equipment send the Port Name
            information using Port ID TLV."
        DEFVAL       { macAddress }
        ::= { ipeCfgPortMainEtherEntry 4 }

    ipeCfgPortNMSVlanTable OBJECT-TYPE
        SYNTAX       SEQUENCE OF IpeCfgPortNMSVlanEntry
        MAX-ACCESS   not-accessible
        STATUS       current
        DESCRIPTION  "NMS VLAN port set up information table."
        ::= { ipeCfgPortGroup 9 }

    ipeCfgPortNMSVlanEntry OBJECT-TYPE
        SYNTAX       IpeCfgPortNMSVlanEntry
        MAX-ACCESS   not-accessible
        STATUS       current
        DESCRIPTION  "entry of NMS VLAN port set up information table."
        INDEX        { ipeCfgPortNMSVlanIfIndex }
        ::= { ipeCfgPortNMSVlanTable 1 }

    IpeCfgPortNMSVlanEntry ::= SEQUENCE {
        ipeCfgPortNMSVlanIfIndex    InterfaceIndex,
        ipeCfgPortNMSVlanNEAddress  IpAddress,
        ipeCfgPortNMSVlanIpAddress  IpAddress,
        ipeCfgPortNMSVlanNetMask    IpAddress,
        ipeCfgPortNMSVlanEnable     EnableDisableValue,
        ipeCfgPortNMSVlanVlanId     Integer32,
        ipeCfgPortNMSVlanCos        Integer32
    }

    ipeCfgPortNMSVlanIfIndex OBJECT-TYPE
        SYNTAX       InterfaceIndex
        MAX-ACCESS   not-accessible
        STATUS       current
        DESCRIPTION  "Index of table."
        ::= { ipeCfgPortNMSVlanEntry 1 }

    ipeCfgPortNMSVlanNEAddress OBJECT-TYPE
        SYNTAX       IpAddress
        MAX-ACCESS   not-accessible
        STATUS       current
        DESCRIPTION  ""
        ::= { ipeCfgPortNMSVlanEntry 2 }

    ipeCfgPortNMSVlanIpAddress OBJECT-TYPE
        SYNTAX       IpAddress
        MAX-ACCESS   read-write
        STATUS       obsolete
        DESCRIPTION  
            "reserved. (IPaddress of NMS VLAN port.
            It makes an error of the Internet Protocol address setting that
            overlaps in the port in the device.
            The object port and the range of the value are described as
            follows.
            Object port: Lct, NMSMngVLAN1-16, Bridge1 )"
        ::= { ipeCfgPortNMSVlanEntry 3 }

    ipeCfgPortNMSVlanNetMask OBJECT-TYPE
        SYNTAX       IpAddress
        MAX-ACCESS   read-write
        STATUS       obsolete
        DESCRIPTION  
            "Reserved. (Subnet mask of NMS VLAN port.
            When it isn't proper as subnetmask, it'll be an error.
            Value range:0x00000000 - 0xfffffffc(0 - 30bit) )"
        ::= { ipeCfgPortNMSVlanEntry 4 }

    ipeCfgPortNMSVlanEnable OBJECT-TYPE
        SYNTAX       EnableDisableValue
        MAX-ACCESS   read-write
        STATUS       current
        DESCRIPTION  
            "NMS VLAN port setting.
            This value is not available (iPASOLINK EX Advanced)."
        DEFVAL       { disable }
        ::= { ipeCfgPortNMSVlanEntry 5 }

    ipeCfgPortNMSVlanVlanId OBJECT-TYPE
        SYNTAX       Integer32 (2..4094)
        MAX-ACCESS   read-write
        STATUS       current
        DESCRIPTION  
            "VLAN ID of NMS VLAN port.
            value range: 2 to 4094
            This value is not available (iPASOLINK EX Advanced)."
        DEFVAL       { 4094 }
        ::= { ipeCfgPortNMSVlanEntry 6 }

    ipeCfgPortNMSVlanCos OBJECT-TYPE
        SYNTAX       Integer32 (0..7)
        MAX-ACCESS   read-write
        STATUS       current
        DESCRIPTION  
            "CoS value of NMS VLAN port
            This value is not available (iPASOLINK EX Advanced)."
        DEFVAL       { 7 }
        ::= { ipeCfgPortNMSVlanEntry 7 }

    ipeCfgBridgeGroup OBJECT IDENTIFIER
        ::= { ipeConfigurationGroup 16 }

    ipeCfgBridgeTable OBJECT-TYPE
        SYNTAX       SEQUENCE OF IpeCfgBridgeEntry
        MAX-ACCESS   not-accessible
        STATUS       current
        DESCRIPTION  "Bridge set up information table."
        ::= { ipeCfgBridgeGroup 1 }

    ipeCfgBridgeEntry OBJECT-TYPE
        SYNTAX       IpeCfgBridgeEntry
        MAX-ACCESS   not-accessible
        STATUS       current
        DESCRIPTION  "entry of  Bridge set up information table."
        INDEX        { ipeCfgBridgeIndex }
        ::= { ipeCfgBridgeTable 1 }

    IpeCfgBridgeEntry ::= SEQUENCE {
        ipeCfgBridgeIndex                      Integer32,
        ipeCfgBridgeNEAddress                  IpAddress,
        ipeCfgBridgeIpAddress                  IpAddress,
        ipeCfgBridgeNetMask                    IpAddress,
        ipeCfgBridgeMtu                        Integer32,
        ipeCfgBridgeLinkLocalAddress           Ipv6Address,
        ipeCfgBridgeLinkLocalAddressOrigin     INTEGER,
        ipeCfgBridgeGlobalAddress              Ipv6Address,
        ipeCfgBridgeGlobalAddressOrigin        INTEGER,
        ipeCfgBridgeGlobalAddressPrefixLength  InetAddressPrefixLength,
        ipeCfgBridgeIpStackMode                INTEGER,
        ipeCfgBridgeSendRouterAdvertisement    INTEGER,
        ipeCfgBridgeRADefaultLifeTime          Integer32,
        ipeCfgBridgeReceiveIcmpRedirects       INTEGER
    }

    ipeCfgBridgeIndex OBJECT-TYPE
        SYNTAX       Integer32 (1..20)
        MAX-ACCESS   not-accessible
        STATUS       current
        DESCRIPTION  "Index of table."
        ::= { ipeCfgBridgeEntry 1 }

    ipeCfgBridgeNEAddress OBJECT-TYPE
        SYNTAX       IpAddress
        MAX-ACCESS   not-accessible
        STATUS       current
        DESCRIPTION  ""
        ::= { ipeCfgBridgeEntry 2 }

    ipeCfgBridgeIpAddress OBJECT-TYPE
        SYNTAX       IpAddress
        MAX-ACCESS   read-write
        STATUS       current
        DESCRIPTION  
            "IPAddress set to bridge.
            Value range:0x00000000 - 0xdfffffff(0.0.0.0 - 223.255.255.255)
            
            It makes an error of the Internet Protocol address setting that
            overlaps in the port in the device.
            It becomes the following about the port of the Internet Protocol
            address repetition check object.
            Object port: Lct, InbandMngVLAN1-16, Bridge1-Bridge20, NE2
            The relation is not in the state and the number of Branch of
            interfaces and the Internet Protocol address repetition check is
            checked.
            
            There can not be relation and it sets, and it refer the number of
            branch.
            When 0.0.0.0 is set to ipeCfgBridgeIpAddress, it becomes an
            Internet Protocol address deletion."
        ::= { ipeCfgBridgeEntry 3 }

    ipeCfgBridgeNetMask OBJECT-TYPE
        SYNTAX       IpAddress
        MAX-ACCESS   read-write
        STATUS       current
        DESCRIPTION  
            "Netmask set to bridge.
            When it isn't proper as subnetmask, it'll be an error.
            Value range:0x00000000 - 0xfffffffc(0 - 30bit)
            
            There can not be relation and it sets, and it refer the number of
            branch."
        ::= { ipeCfgBridgeEntry 4 }

    ipeCfgBridgeMtu OBJECT-TYPE
        SYNTAX       Integer32 (256..1500)
        MAX-ACCESS   read-write
        STATUS       current
        DESCRIPTION  
            "MTU value of bridge.
            value range:256 to 1500
            
            There can not be relation and it sets, and it refer the number of
            branch."
        ::= { ipeCfgBridgeEntry 5 }

    ipeCfgBridgeLinkLocalAddress OBJECT-TYPE
        SYNTAX       Ipv6Address
        MAX-ACCESS   read-write
        STATUS       current
        DESCRIPTION  "IPv6 Link-local Address set to bridge."
        ::= { ipeCfgBridgeEntry 6 }

    ipeCfgBridgeLinkLocalAddressOrigin OBJECT-TYPE
        SYNTAX       INTEGER { invalid(0), manual(1), linklayer(2) }
        MAX-ACCESS   read-write
        STATUS       current
        DESCRIPTION  
            "The origin of the address.
                manual(1) indicates that the address was manually 
            configured to a specified address, e.g., by user 
            configuration.
            
                linklayer(2) indicates the address to be created 
            by IPv6 stateless address auto-configuration."
        DEFVAL       { linklayer }
        ::= { ipeCfgBridgeEntry 7 }

    ipeCfgBridgeGlobalAddress OBJECT-TYPE
        SYNTAX       Ipv6Address
        MAX-ACCESS   read-write
        STATUS       current
        DESCRIPTION  
            "The IPv6 global address of this interface.
                     The following are not valid addresses:
                        ::1/128 IPv6 Loopback
                        FE80::/10 Link local
                        FF00::/8 IPv6 Multicasts"
        ::= { ipeCfgBridgeEntry 8 }

    ipeCfgBridgeGlobalAddressOrigin OBJECT-TYPE
        SYNTAX       INTEGER { invalid(0), manual(1), linklayer(4) }
        MAX-ACCESS   read-write
        STATUS       current
        DESCRIPTION  
            "The origin of the address.
               manual(1) indicates that the address was manually
                       configured to a specified address, e.g., by user 
                       configuration. 
            
               linklayer(4) indicates an address created based on the 
                       prefix received from Router Advertisement and this
                       interface is considered as Host interface.
            dhcp(5)      indicates an address created by DHCP."
        DEFVAL       { linklayer }
        ::= { ipeCfgBridgeEntry 9 }

    ipeCfgBridgeGlobalAddressPrefixLength OBJECT-TYPE
        SYNTAX       InetAddressPrefixLength
        MAX-ACCESS   read-write
        STATUS       current
        DESCRIPTION  "The prefix length of Global Address."
        ::= { ipeCfgBridgeEntry 10 }

    ipeCfgBridgeIpStackMode OBJECT-TYPE
        SYNTAX       INTEGER { ipv4(1), ipv6(2), dual(3) }
        MAX-ACCESS   read-write
        STATUS       current
        DESCRIPTION  
            "Indicate IP Stack mode of this interface.
            
            ipv4 : Enable IPv4 support on this interface.
            ipv6 : Enable IPv6 support on this interface.
            dual : Enable IPv4 and IPv6 support on this interface.
            
            Note that ipeCfgBridgeIpStackMode: ipv4(1) and
            ipeSysIpv4DropFilterEnable: enable(2) cannot be set for the
            establishment of IPv4 communication."
        ::= { ipeCfgBridgeEntry 11 }

    ipeCfgBridgeSendRouterAdvertisement OBJECT-TYPE
        SYNTAX       INTEGER { invalid(0), true(1), false(2) }
        MAX-ACCESS   read-write
        STATUS       current
        DESCRIPTION  
            "A flag indicating whether the router sends periodic
            router advertisements and responds to router solicitations
            on this interface."
        ::= { ipeCfgBridgeEntry 12 }

    ipeCfgBridgeRADefaultLifeTime OBJECT-TYPE
        SYNTAX       Integer32 (0|600..9000)
        MAX-ACCESS   read-write
        STATUS       current
        DESCRIPTION  
            "The value to be placed in the router lifetime field of
            router advertisements sent from this interface. 
            This value must be either 0 or between
            ipv6RouterAdvertMaxInterval and
            9000 seconds.
            
            A value of zero indicates that the router is not to be used
            as a default router.
            
            The default is 3 * ipv6RouterAdvertMaxInterval."
        ::= { ipeCfgBridgeEntry 13 }

    ipeCfgBridgeReceiveIcmpRedirects OBJECT-TYPE
        SYNTAX       INTEGER { invalid(0), true(1), false(2) }
        MAX-ACCESS   read-write
        STATUS       current
        DESCRIPTION  
            "The true/false value to process received ICMP Redirect
            messages from this bridge.
            For router, this object will always be false as router
            does not process Redirects."
        ::= { ipeCfgBridgeEntry 14 }

    ipeCfgBridgePortTable OBJECT-TYPE
        SYNTAX       SEQUENCE OF IpeCfgBridgePortEntry
        MAX-ACCESS   not-accessible
        STATUS       current
        DESCRIPTION  "Bridge set up information table."
        ::= { ipeCfgBridgeGroup 2 }

    ipeCfgBridgePortEntry OBJECT-TYPE
        SYNTAX       IpeCfgBridgePortEntry
        MAX-ACCESS   not-accessible
        STATUS       current
        DESCRIPTION  "entry of  Bridge set up information table."
        INDEX        { ipeCfgBridgePortIfIndex }
        ::= { ipeCfgBridgePortTable 1 }

    IpeCfgBridgePortEntry ::= SEQUENCE {
        ipeCfgBridgePortIfIndex      InterfaceIndex,
        ipeCfgBridgePortNEAddress    IpAddress,
        ipeCfgBridgePortBridgeIndex  Integer32
    }

    ipeCfgBridgePortIfIndex OBJECT-TYPE
        SYNTAX       InterfaceIndex
        MAX-ACCESS   not-accessible
        STATUS       current
        DESCRIPTION  
            "The interface identified by a particular value of this index is
            the same interface as identified by the same value of ifIndex.
            Valid Value(NMS,NE1,E1,RADIO00-10,InbandMngVLAN1-16)"
        ::= { ipeCfgBridgePortEntry 1 }

    ipeCfgBridgePortNEAddress OBJECT-TYPE
        SYNTAX       IpAddress
        MAX-ACCESS   not-accessible
        STATUS       current
        DESCRIPTION  ""
        ::= { ipeCfgBridgePortEntry 2 }

    ipeCfgBridgePortBridgeIndex OBJECT-TYPE
        SYNTAX       Integer32 (0..20)
        MAX-ACCESS   read-write
        STATUS       current
        DESCRIPTION  "Index value of bridge."
        ::= { ipeCfgBridgePortEntry 3 }

    ipeCfgBridgeVlanTable OBJECT-TYPE
        SYNTAX       SEQUENCE OF IpeCfgBridgeVlanEntry
        MAX-ACCESS   not-accessible
        STATUS       current
        DESCRIPTION  "Bridge set up information table."
        ::= { ipeCfgBridgeGroup 3 }

    ipeCfgBridgeVlanEntry OBJECT-TYPE
        SYNTAX       IpeCfgBridgeVlanEntry
        MAX-ACCESS   not-accessible
        STATUS       current
        DESCRIPTION  "entry of  Bridge set up information table."
        INDEX        { ipeCfgBridgeVlanIndex }
        ::= { ipeCfgBridgeVlanTable 1 }

    IpeCfgBridgeVlanEntry ::= SEQUENCE {
        ipeCfgBridgeVlanIndex      Integer32,
        ipeCfgBridgeVlanNEAddress  IpAddress,
        ipeCfgBridgeVlanVlanId     Integer32
    }

    ipeCfgBridgeVlanIndex OBJECT-TYPE
        SYNTAX       Integer32 (1..20)
        MAX-ACCESS   not-accessible
        STATUS       current
        DESCRIPTION  "Index of table."
        ::= { ipeCfgBridgeVlanEntry 1 }

    ipeCfgBridgeVlanNEAddress OBJECT-TYPE
        SYNTAX       IpAddress
        MAX-ACCESS   not-accessible
        STATUS       current
        DESCRIPTION  ""
        ::= { ipeCfgBridgeVlanEntry 2 }

    ipeCfgBridgeVlanVlanId OBJECT-TYPE
        SYNTAX       Integer32 (0..4094)
        MAX-ACCESS   read-write
        STATUS       current
        DESCRIPTION  
            "VLAN ID of Bridge.
            value range : 1 - 4094, notUsed(0)"
        ::= { ipeCfgBridgeVlanEntry 3 }

    ipeCfgPripGroup OBJECT IDENTIFIER
        ::= { ipeConfigurationGroup 17 }

    ipeCfgPripTable OBJECT-TYPE
        SYNTAX       SEQUENCE OF IpeCfgPripEntry
        MAX-ACCESS   not-accessible
        STATUS       current
        DESCRIPTION  "PRIP set up information table."
        ::= { ipeCfgPripGroup 1 }

    ipeCfgPripEntry OBJECT-TYPE
        SYNTAX       IpeCfgPripEntry
        MAX-ACCESS   not-accessible
        STATUS       current
        DESCRIPTION  "entry of PRIP set up information table."
        INDEX        { ipeCfgPripIndex }
        ::= { ipeCfgPripTable 1 }

    IpeCfgPripEntry ::= SEQUENCE {
        ipeCfgPripIndex        Integer32,
        ipeCfgPripNEAddress    IpAddress,
        ipeCfgPripRouteEnable  INTEGER,
        ipeCfgPripUdpPort      INTEGER
    }

    ipeCfgPripIndex OBJECT-TYPE
        SYNTAX       Integer32 (1..1)
        MAX-ACCESS   not-accessible
        STATUS       current
        DESCRIPTION  
            "Index of this ipeCfgPripEntry.
            It's a fiexed value(= 1)."
        ::= { ipeCfgPripEntry 1 }

    ipeCfgPripNEAddress OBJECT-TYPE
        SYNTAX       IpAddress
        MAX-ACCESS   not-accessible
        STATUS       current
        DESCRIPTION  ""
        ::= { ipeCfgPripEntry 2 }

    ipeCfgPripRouteEnable OBJECT-TYPE
        SYNTAX       INTEGER { invalid(0), enabled(1), disabled(2) }
        MAX-ACCESS   read-write
        STATUS       current
        DESCRIPTION  
            "Enable or disables PRIP.
            
            enabled(1):PRIP is enabled. 
            disabled(2):PRIP is disabled."
        ::= { ipeCfgPripEntry 3 }

    ipeCfgPripUdpPort OBJECT-TYPE
        SYNTAX       INTEGER { ripdefaultport(520), pripdefaultport(8520) }
        MAX-ACCESS   read-write
        STATUS       current
        DESCRIPTION  
            "Setting of UDP port number used with PRIP.
            
            Either of 8520 or 520 is set.
            
            This setting is valid since PRIP will start next time."
        ::= { ipeCfgPripEntry 4 }

    ipeCfgPripPortTable OBJECT-TYPE
        SYNTAX       SEQUENCE OF IpeCfgPripPortEntry
        MAX-ACCESS   not-accessible
        STATUS       current
        DESCRIPTION  "PRIP set up information table.(per port)"
        ::= { ipeCfgPripGroup 2 }

    ipeCfgPripPortEntry OBJECT-TYPE
        SYNTAX       IpeCfgPripPortEntry
        MAX-ACCESS   not-accessible
        STATUS       current
        DESCRIPTION  "entry of PRIP set up information table.(per port)"
        INDEX        { ipeCfgPripPortIfIndex }
        ::= { ipeCfgPripPortTable 1 }

    IpeCfgPripPortEntry ::= SEQUENCE {
        ipeCfgPripPortIfIndex             InterfaceIndex,
        ipeCfgPripPortNEAddress           IpAddress,
        ipeCfgPripPortEnable              INTEGER,
        ipeCfgPripPortPropagateNetEnable  INTEGER
    }

    ipeCfgPripPortIfIndex OBJECT-TYPE
        SYNTAX       InterfaceIndex
        MAX-ACCESS   not-accessible
        STATUS       current
        DESCRIPTION  "Index of table."
        ::= { ipeCfgPripPortEntry 1 }

    ipeCfgPripPortNEAddress OBJECT-TYPE
        SYNTAX       IpAddress
        MAX-ACCESS   not-accessible
        STATUS       current
        DESCRIPTION  ""
        ::= { ipeCfgPripPortEntry 2 }

    ipeCfgPripPortEnable OBJECT-TYPE
        SYNTAX       INTEGER { invalid(0), enabled(1), disabled(2) }
        MAX-ACCESS   read-write
        STATUS       current
        DESCRIPTION  
            "Setting of some port when PRIP will be enabled.
            
            enabled(1)  : this port is enabled.
            disabled(2) : this port is disable."
        ::= { ipeCfgPripPortEntry 3 }

    ipeCfgPripPortPropagateNetEnable OBJECT-TYPE
        SYNTAX       INTEGER { invalid(0), enabled(1), disabled(2) }
        MAX-ACCESS   read-write
        STATUS       current
        DESCRIPTION  
            "Propagate setting for neighbor NE.
            
            enabled(1)  : this port is propagated.
            disabled(2) : this port is not propagated.
                          (Do not register in the RIP route.)"
        ::= { ipeCfgPripPortEntry 4 }

    ipeCfgNaptGroup OBJECT IDENTIFIER
        ::= { ipeConfigurationGroup 18 }

    ipeCfgNaptTable OBJECT-TYPE
        SYNTAX       SEQUENCE OF IpeCfgNaptEntry
        MAX-ACCESS   not-accessible
        STATUS       current
        DESCRIPTION  "NAPT set up information table."
        ::= { ipeCfgNaptGroup 1 }

    ipeCfgNaptEntry OBJECT-TYPE
        SYNTAX       IpeCfgNaptEntry
        MAX-ACCESS   not-accessible
        STATUS       current
        DESCRIPTION  "entry of  NAPT set up information table."
        INDEX        { ipeCfgNaptIndex }
        ::= { ipeCfgNaptTable 1 }

    IpeCfgNaptEntry ::= SEQUENCE {
        ipeCfgNaptIndex      Integer32,
        ipeCfgNaptNEAddress  IpAddress,
        ipeCfgNaptEnable     INTEGER
    }

    ipeCfgNaptIndex OBJECT-TYPE
        SYNTAX       Integer32 (1..1)
        MAX-ACCESS   not-accessible
        STATUS       current
        DESCRIPTION  
            "Index of this ipeCfgNaptEntry.
            It's a fixed value(=1)."
        ::= { ipeCfgNaptEntry 1 }

    ipeCfgNaptNEAddress OBJECT-TYPE
        SYNTAX       IpAddress
        MAX-ACCESS   not-accessible
        STATUS       current
        DESCRIPTION  ""
        ::= { ipeCfgNaptEntry 2 }

    ipeCfgNaptEnable OBJECT-TYPE
        SYNTAX       INTEGER { enabled(1), disabled(2), neighbor(3) }
        MAX-ACCESS   read-write
        STATUS       current
        DESCRIPTION  
            "Address translation invalid effective/setting by NAPT.
            value range: enabled
                        disabled"
        ::= { ipeCfgNaptEntry 3 }

    ipeCfgStaticRouteGroup OBJECT IDENTIFIER
        ::= { ipeConfigurationGroup 19 }

    ipeCfgStaticRouteTable OBJECT-TYPE
        SYNTAX       SEQUENCE OF IpeCfgStaticRouteEntry
        MAX-ACCESS   not-accessible
        STATUS       current
        DESCRIPTION  "Static Routing set up information table."
        ::= { ipeCfgStaticRouteGroup 1 }

    ipeCfgStaticRouteEntry OBJECT-TYPE
        SYNTAX       IpeCfgStaticRouteEntry
        MAX-ACCESS   not-accessible
        STATUS       current
        DESCRIPTION  "entry of  Static Routing set up information table."
        INDEX        { ipeCfgRouteIndex }
        ::= { ipeCfgStaticRouteTable 1 }

    IpeCfgStaticRouteEntry ::= SEQUENCE {
        ipeCfgRouteIndex      Integer32,
        ipeCfgRouteNEAddress  IpAddress,
        ipeCfgRouteDest       IpAddress,
        ipeCfgRouteMask       IpAddress,
        ipeCfgRouteNextHop    IpAddress,
        ipeCfgRouteRowStatus  RowStatus
    }

    ipeCfgRouteIndex OBJECT-TYPE
        SYNTAX       Integer32 (1..128)
        MAX-ACCESS   not-accessible
        STATUS       current
        DESCRIPTION  "Index of table(1 to 128)."
        ::= { ipeCfgStaticRouteEntry 1 }

    ipeCfgRouteNEAddress OBJECT-TYPE
        SYNTAX       IpAddress
        MAX-ACCESS   not-accessible
        STATUS       current
        DESCRIPTION  ""
        ::= { ipeCfgStaticRouteEntry 2 }

    ipeCfgRouteDest OBJECT-TYPE
        SYNTAX       IpAddress
        MAX-ACCESS   read-create
        STATUS       current
        DESCRIPTION  
            "Static routing object destination address.
            When masking in ipeCfgRouteMask, the host address part has to be
            a zero, if any.
            Value range:0x00000000-0xdfffffff(0.0.0.0-223.255.255.255)
            The value acquisition when unsetting it returns NoSuchObject."
        ::= { ipeCfgStaticRouteEntry 3 }

    ipeCfgRouteMask OBJECT-TYPE
        SYNTAX       IpAddress
        MAX-ACCESS   read-create
        STATUS       current
        DESCRIPTION  
            "Static routing object subnet mask.
            When it isn't proper as subnetmask, it'll be an error.
            Value range:0x00000000-0xffffffff(0-32bit)
            Only when ipeCfgRouteDest is 0, 0bit is allowed.
            The value acquisition when unsetting it returns NoSuchObject."
        ::= { ipeCfgStaticRouteEntry 4 }

    ipeCfgRouteNextHop OBJECT-TYPE
        SYNTAX       IpAddress
        MAX-ACCESS   read-create
        STATUS       current
        DESCRIPTION  
            "Static routing object gateway address.
            Value range:0x00000001 - 0xdfffffff(0.0.0.1 - 223.255.255.255)
            The value acquisition when unsetting it returns NoSuchObject."
        ::= { ipeCfgStaticRouteEntry 5 }

    ipeCfgRouteRowStatus OBJECT-TYPE
        SYNTAX       RowStatus { active(1), createAndGo(4), destroy(6) }
        MAX-ACCESS   read-create
        STATUS       current
        DESCRIPTION  
            "This RowStatus has a status only 'active(1)'. 
            
            1) creating a entry
            When you make a new entry, you must SET objects indicated below.
            * ipeCfgRouteDest
            * ipeCfgRouteMask
            * ipeCfgRouteNextHop
            * ipeCfgRouteRowStatus <- createAndGo(4)
            
            2) modifing a entry
            When you make a existing entry, you must SET objects indicated
            below.
            * ipeCfgRouteDest
            * ipeCfgRouteMask
            * ipeCfgRouteNextHop
            
            3) deleting a entry
            When you SET a destroy(6) to ipeCfgRouteRowStatus, the entry is
            destroyed.
            * ipeCfgRouteRowStatus <- destory(6)"
        ::= { ipeCfgStaticRouteEntry 6 }

    ipeCfgV6StaticRouteTable OBJECT-TYPE
        SYNTAX       SEQUENCE OF IpeCfgV6StaticRouteEntry
        MAX-ACCESS   not-accessible
        STATUS       current
        DESCRIPTION  "IPv6 Static Routing set up information table."
        ::= { ipeCfgStaticRouteGroup 2 }

    ipeCfgV6StaticRouteEntry OBJECT-TYPE
        SYNTAX       IpeCfgV6StaticRouteEntry
        MAX-ACCESS   not-accessible
        STATUS       current
        DESCRIPTION  "entry of Static Routing set up information table."
        INDEX        { ipeCfgV6RouteIndex }
        ::= { ipeCfgV6StaticRouteTable 1 }

    IpeCfgV6StaticRouteEntry ::= SEQUENCE {
        ipeCfgV6RouteIndex           Integer32,
        ipeCfgV6RouteNEAddress       IpAddress,
        ipeCfgV6RouteDest            Ipv6Address,
        ipeCfgV6RoutePrefixLength    InetAddressPrefixLength,
        ipeCfgV6RouteNextHop         Ipv6Address,
        ipeCfgV6RouteNextHopIfIndex  INTEGER,
        ipeCfgV6RouteRowStatus       RowStatus
    }

    ipeCfgV6RouteIndex OBJECT-TYPE
        SYNTAX       Integer32 (1..128)
        MAX-ACCESS   not-accessible
        STATUS       current
        DESCRIPTION  "Index of table(1 to 128)."
        ::= { ipeCfgV6StaticRouteEntry 1 }

    ipeCfgV6RouteNEAddress OBJECT-TYPE
        SYNTAX       IpAddress
        MAX-ACCESS   not-accessible
        STATUS       current
        DESCRIPTION  ""
        ::= { ipeCfgV6StaticRouteEntry 2 }

    ipeCfgV6RouteDest OBJECT-TYPE
        SYNTAX       Ipv6Address
        MAX-ACCESS   read-create
        STATUS       current
        DESCRIPTION  
            "Static routing object destination address.
            The value acquisition when unsetting it returns NoSuchObject."
        ::= { ipeCfgV6StaticRouteEntry 3 }

    ipeCfgV6RoutePrefixLength OBJECT-TYPE
        SYNTAX       InetAddressPrefixLength
        MAX-ACCESS   read-create
        STATUS       current
        DESCRIPTION  
            "Static routing object prefix length.
            When it isn't proper as prefix length, it'll be an error.
            Only when ipeCfgV6RouteDest is 0, 0bit is allowed.
            The value acquisition when unsetting it returns NoSuchObject."
        ::= { ipeCfgV6StaticRouteEntry 4 }

    ipeCfgV6RouteNextHop OBJECT-TYPE
        SYNTAX       Ipv6Address
        MAX-ACCESS   read-create
        STATUS       current
        DESCRIPTION  
            "Static routing object gateway address.
            The value acquisition when unsetting it returns NoSuchObject."
        ::= { ipeCfgV6StaticRouteEntry 5 }

    ipeCfgV6RouteNextHopIfIndex OBJECT-TYPE
        SYNTAX       INTEGER {
                         any(0),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "Static routing object gateway interface index.
            When ipeCfgV6RouteNextHop is specified, setting this value is not
            considered.
            
            When setting Link-local address for ipeCfgV6RouteNextHop, this 
            object must be configured.
            
            The value acquisition when unsetting it returns NoSuchObject."
        ::= { ipeCfgV6StaticRouteEntry 6 }

    ipeCfgV6RouteRowStatus OBJECT-TYPE
        SYNTAX       RowStatus { active(1), createAndGo(4), destroy(6) }
        MAX-ACCESS   read-create
        STATUS       current
        DESCRIPTION  
            "This RowStatus has a status only 'active(1)'. 
            
            1) creating a entry
            When you make a new entry, you must SET objects indicated below.
            * ipeCfgV6RouteDest
            * ipeCfgV6RoutePrefixLength
            * ipeCfgV6RouteNextHop
            * ipeCfgV6RouteNextHopIfIndex
            * ipeCfgV6RouteRowStatus <- createAndGo(4)
            
            2) modifing a entry
            When you make a existing entry, you must SET objects indicated
            below.
            * ipeCfgV6RouteDest
            * ipeCfgV6RoutePrefixLength
            * ipeCfgV6RouteNextHop
            * ipeCfgV6RouteNextHopIfIndex
            
            3) deleting a entry
            When you SET a destroy(6) to ipeCfgV6RouteRowStatus, the entry is
            destroyed.
            * ipeCfgV6RouteRowStatus <- destory(6)"
        ::= { ipeCfgV6StaticRouteEntry 7 }

    ipeCfgLog OBJECT IDENTIFIER
        ::= { ipeConfigurationGroup 20 }

    ipeCfgSyslogTable OBJECT-TYPE
        SYNTAX       SEQUENCE OF IpeCfgSyslogEntry
        MAX-ACCESS   not-accessible
        STATUS       current
        DESCRIPTION  "Remote log set up information table."
        ::= { ipeCfgLog 1 }

    ipeCfgSyslogEntry OBJECT-TYPE
        SYNTAX       IpeCfgSyslogEntry
        MAX-ACCESS   not-accessible
        STATUS       current
        DESCRIPTION  "Entry of remote log set up information table."
        INDEX        { ipeCfgSyslogIndex }
        ::= { ipeCfgSyslogTable 1 }

    IpeCfgSyslogEntry ::= SEQUENCE {
        ipeCfgSyslogIndex         Integer32,
        ipeCfgSyslogNEAddress     IpAddress,
        ipeCfgSyslogServiceUsage  EnableDisableValue
    }

    ipeCfgSyslogIndex OBJECT-TYPE
        SYNTAX       Integer32 (1..1)
        MAX-ACCESS   not-accessible
        STATUS       current
        DESCRIPTION  "Index of table(1)."
        ::= { ipeCfgSyslogEntry 1 }

    ipeCfgSyslogNEAddress OBJECT-TYPE
        SYNTAX       IpAddress
        MAX-ACCESS   not-accessible
        STATUS       current
        DESCRIPTION  ""
        ::= { ipeCfgSyslogEntry 2 }

    ipeCfgSyslogServiceUsage OBJECT-TYPE
        SYNTAX       EnableDisableValue
        MAX-ACCESS   read-write
        STATUS       current
        DESCRIPTION  "Syslog transfering is enable or disable"
        ::= { ipeCfgSyslogEntry 3 }

    ipeCfgSyslogServerTable OBJECT-TYPE
        SYNTAX       SEQUENCE OF IpeCfgSyslogServerEntry
        MAX-ACCESS   not-accessible
        STATUS       current
        DESCRIPTION  "Syslog server set up information table."
        ::= { ipeCfgLog 3 }

    ipeCfgSyslogServerEntry OBJECT-TYPE
        SYNTAX       IpeCfgSyslogServerEntry
        MAX-ACCESS   not-accessible
        STATUS       current
        DESCRIPTION  "Entry of syslog server set up information table."
        INDEX        { ipeCfgSyslogServerIndex }
        ::= { ipeCfgSyslogServerTable 1 }

    IpeCfgSyslogServerEntry ::= SEQUENCE {
        ipeCfgSyslogServerIndex          INTEGER,
        ipeCfgSyslogServerNEAddress      IpAddress,
        ipeCfgSyslogServerRowStatus      RowStatus,
        ipeCfgSyslogServerFacility       OCTET STRING,
        ipeCfgSyslogServerIpAddressType  InetAddressType,
        ipeCfgSyslogServerIpAddress      InetAddress,
        ipeCfgSyslogServerInterface      INTEGER,
        ipeCfgSyslogServerProtocolType   INTEGER,
        ipeCfgSyslogServerPort           Integer32,
        ipeCfgSyslogServerTlsUsage       EnableDisableValue
    }

    ipeCfgSyslogServerIndex OBJECT-TYPE
        SYNTAX       INTEGER { server1(1), server2(2), server3(3) }
        MAX-ACCESS   not-accessible
        STATUS       current
        DESCRIPTION  "Index of table(1 to 3)"
        ::= { ipeCfgSyslogServerEntry 1 }

    ipeCfgSyslogServerNEAddress OBJECT-TYPE
        SYNTAX       IpAddress
        MAX-ACCESS   not-accessible
        STATUS       current
        DESCRIPTION  ""
        ::= { ipeCfgSyslogServerEntry 2 }

    ipeCfgSyslogServerRowStatus OBJECT-TYPE
        SYNTAX       RowStatus
        MAX-ACCESS   read-create
        STATUS       current
        DESCRIPTION  "Rowstatus for this table."
        ::= { ipeCfgSyslogServerEntry 3 }

    ipeCfgSyslogServerFacility OBJECT-TYPE
        SYNTAX       OCTET STRING (SIZE(4..4))
        MAX-ACCESS   read-create
        STATUS       current
        DESCRIPTION  
            "Current operational values of facility in syslog server.
            SYNTAX is 32bit string. The definition of each bit is shown
            below.
            
             bit0 : kern
             bit1 : user
             bit2 : mail
             bit3 : daemon
             bit4 : auth
             bit5 : syslog
             bit6 : lpr
             bit7 : news
             bit8 : uucp
             bit9 : cron
             bit10: authpriv
             bit11: ftp
             bit16: local0
             bit17: local1
             bit18: local2
            
             other: reserved (don't care)
            
            Example)
             the pattern of kern, local0, local1, and local2.
             ipeCfgSyslogServerFacility = 'Hex-STRING: 01 00 07 00'"
        ::= { ipeCfgSyslogServerEntry 4 }

    ipeCfgSyslogServerIpAddressType OBJECT-TYPE
        SYNTAX       InetAddressType
        MAX-ACCESS   read-create
        STATUS       current
        DESCRIPTION  
            "Syslog server IP address type.
            The type of ipeCfgSyslogServerIpAddress."
        ::= { ipeCfgSyslogServerEntry 5 }

    ipeCfgSyslogServerIpAddress OBJECT-TYPE
        SYNTAX       InetAddress
        MAX-ACCESS   read-create
        STATUS       current
        DESCRIPTION  
            "Syslog server IP address.
            The address type of this object is specified in
            ipeCfgSyslogServerIpAddressType."
        ::= { ipeCfgSyslogServerEntry 6 }

    ipeCfgSyslogServerInterface OBJECT-TYPE
        SYNTAX       INTEGER {
                         notAssign(0),
                         lct(2),
                         bridge01(11),
                         bridge02(12),
                         bridge03(13),
                         bridge04(14),
                         bridge05(15),
                         bridge06(16),
                         bridge07(17),
                         bridge08(18),
                         bridge09(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "Syslog server interface for when ipeCfgSyslogServerIpAddressType
            is ipv6."
        ::= { ipeCfgSyslogServerEntry 7 }

    ipeCfgSyslogServerProtocolType OBJECT-TYPE
        SYNTAX       INTEGER { invalid(0), tcp(1), udp(2) }
        MAX-ACCESS   read-create
        STATUS       current
        DESCRIPTION  "Syslog server protocol type."
        ::= { ipeCfgSyslogServerEntry 8 }

    ipeCfgSyslogServerPort OBJECT-TYPE
        SYNTAX       Integer32 (1..65535)
        MAX-ACCESS   read-create
        STATUS       current
        DESCRIPTION  "Syslog server port number."
        ::= { ipeCfgSyslogServerEntry 9 }

    ipeCfgSyslogServerTlsUsage OBJECT-TYPE
        SYNTAX       EnableDisableValue
        MAX-ACCESS   read-create
        STATUS       current
        DESCRIPTION  "Syslog server TLS usage."
        ::= { ipeCfgSyslogServerEntry 10 }

    ipeCfgSyslogTrapMapTable OBJECT-TYPE
        SYNTAX       SEQUENCE OF IpeCfgSyslogTrapMapEntry
        MAX-ACCESS   not-accessible
        STATUS       current
        DESCRIPTION  
            "Mapping information table between syslog and SNMP Trap."
        ::= { ipeCfgLog 4 }

    ipeCfgSyslogTrapMapEntry OBJECT-TYPE
        SYNTAX       IpeCfgSyslogTrapMapEntry
        MAX-ACCESS   not-accessible
        STATUS       current
        DESCRIPTION  ""
        INDEX        { ipeCfgSyslogTrapMapIndex }
        ::= { ipeCfgSyslogTrapMapTable 1 }

    IpeCfgSyslogTrapMapEntry ::= SEQUENCE {
        ipeCfgSyslogTrapMapIndex      INTEGER,
        ipeCfgSyslogTrapMapNEAddress  IpAddress,
        ipeCfgSyslogTrapMapSeverity   INTEGER
    }

    ipeCfgSyslogTrapMapIndex OBJECT-TYPE
        SYNTAX       INTEGER {
                         almCrit(1),
                         almMajor(2),
                         almMinor(3),
                         almWarn(4),
                         almInfo(5),
                         staInfo(6),
                         ctlInfo(7)
                     }
        MAX-ACCESS   not-accessible
        STATUS       current
        DESCRIPTION  
            "Index of table(1 to 7)
            This object corresponds to SNMP trap severity."
        ::= { ipeCfgSyslogTrapMapEntry 1 }

    ipeCfgSyslogTrapMapNEAddress OBJECT-TYPE
        SYNTAX       IpAddress
        MAX-ACCESS   not-accessible
        STATUS       current
        DESCRIPTION  ""
        ::= { ipeCfgSyslogTrapMapEntry 2 }

    ipeCfgSyslogTrapMapSeverity OBJECT-TYPE
        SYNTAX       INTEGER {
                         emergency(0),
                         alert(1),
                         critical(2),
                         error(3),
                         warning(4),
                         notice(5),
                         informational(6),
                         debug(7)
                     }
        MAX-ACCESS   read-write
        STATUS       current
        DESCRIPTION  
            "Severity mapping between syslog severity and SNMP trap severity.
            This object corresponds to syslog severity.
            --
            Index:DefaultValue
            almCrit(1):critical
            almMajor(2):error
            almMinor(3):warning
            almWarn(4):notice
            almInfo(5):informational
            staInfo(6):informational
            ctlInfo(7):informational"
        ::= { ipeCfgSyslogTrapMapEntry 3 }

    ipeCfgSyslogSeverityTable OBJECT-TYPE
        SYNTAX       SEQUENCE OF IpeCfgSyslogSeverityEntry
        MAX-ACCESS   not-accessible
        STATUS       current
        DESCRIPTION  
            "Mapping information table between syslog and SNMP Trap."
        ::= { ipeCfgLog 5 }

    ipeCfgSyslogSeverityEntry OBJECT-TYPE
        SYNTAX       IpeCfgSyslogSeverityEntry
        MAX-ACCESS   not-accessible
        STATUS       current
        DESCRIPTION  
            "Mapping information table between syslog and SNMP Trap."
        INDEX        {
                         ipeCfgSyslogSeverityServerIndex,
                         ipeCfgSyslogSeverityFacilIndex
                     }
        ::= { ipeCfgSyslogSeverityTable 1 }

    IpeCfgSyslogSeverityEntry ::= SEQUENCE {
        ipeCfgSyslogSeverityServerIndex  INTEGER,
        ipeCfgSyslogSeverityFacilIndex   INTEGER,
        ipeCfgSyslogSeverityNEAddress    IpAddress,
        ipeCfgSyslogSeverity             INTEGER
    }

    ipeCfgSyslogSeverityServerIndex OBJECT-TYPE
        SYNTAX       INTEGER { server1(1), server2(2), server3(3) }
        MAX-ACCESS   not-accessible
        STATUS       current
        DESCRIPTION  "Server Index of table(1 to 3)"
        ::= { ipeCfgSyslogSeverityEntry 1 }

    ipeCfgSyslogSeverityFacilIndex OBJECT-TYPE
        SYNTAX       INTEGER {
                         kern(1),
                         user(2),
                         mail(3),
                         daemon(4),
                         auth(5),
                         syslog(6),
                         lpr(7),
                         news(8),
                         uucp(9),
                         cron(10),
                         authpriv(11),
                         ftp(12),
                         local0(17),
                         local1(18),
                         local2(19)
                     }
        MAX-ACCESS   not-accessible
        STATUS       current
        DESCRIPTION  "Facility Index of table(1 to 12 and 17 to 19)"
        ::= { ipeCfgSyslogSeverityEntry 2 }

    ipeCfgSyslogSeverityNEAddress OBJECT-TYPE
        SYNTAX       IpAddress
        MAX-ACCESS   not-accessible
        STATUS       current
        DESCRIPTION  ""
        ::= { ipeCfgSyslogSeverityEntry 3 }

    ipeCfgSyslogSeverity OBJECT-TYPE
        SYNTAX       INTEGER {
                         emergency(0),
                         alert(1),
                         critical(2),
                         error(3),
                         warning(4),
                         notice(5),
                         informational(6),
                         debug(7)
                     }
        MAX-ACCESS   read-write
        STATUS       current
        DESCRIPTION  
            "Syslog server severity threshold for each facility.
            Default value is informational for all facility index."
        ::= { ipeCfgSyslogSeverityEntry 4 }

    ipeCfgAccessListGroup OBJECT IDENTIFIER
        ::= { ipeConfigurationGroup 21 }

    ipeCfgAccessListRuleTable OBJECT-TYPE
        SYNTAX       SEQUENCE OF IpeCfgAccessListRuleEntry
        MAX-ACCESS   not-accessible
        STATUS       current
        DESCRIPTION  "Table of Access List(Rule)."
        ::= { ipeCfgAccessListGroup 1 }

    ipeCfgAccessListRuleEntry OBJECT-TYPE
        SYNTAX       IpeCfgAccessListRuleEntry
        MAX-ACCESS   not-accessible
        STATUS       current
        DESCRIPTION  "Entry of Access List(Rule)."
        INDEX        { ipeCfgAccessListRuleEnableIndex }
        ::= { ipeCfgAccessListRuleTable 1 }

    IpeCfgAccessListRuleEntry ::= SEQUENCE {
        ipeCfgAccessListRuleEnableIndex         Integer32,
        ipeCfgAccessListRuleNEAddress           IpAddress,
        ipeCfgAccessListInputRuleEnable         INTEGER,
        ipeCfgAccessListForwardRuleEnable       INTEGER,
        ipeCfgAccessListInputDefaultAction      INTEGER,
        ipeCfgAccessListForwardDefaultAction    INTEGER,
        ipeCfgAccessListV6InputRuleEnable       INTEGER,
        ipeCfgAccessListV6ForwardRuleEnable     INTEGER,
        ipeCfgAccessListV6InputDefaultAction    INTEGER,
        ipeCfgAccessListV6ForwardDefaultAction  INTEGER
    }

    ipeCfgAccessListRuleEnableIndex OBJECT-TYPE
        SYNTAX       Integer32 (1..1)
        MAX-ACCESS   not-accessible
        STATUS       current
        DESCRIPTION  
            "Index of this ipeCfgAccessListRuleEntry.
            It's a fixed value(=1)."
        ::= { ipeCfgAccessListRuleEntry 1 }

    ipeCfgAccessListRuleNEAddress OBJECT-TYPE
        SYNTAX       IpAddress
        MAX-ACCESS   not-accessible
        STATUS       current
        DESCRIPTION  ""
        ::= { ipeCfgAccessListRuleEntry 2 }

    ipeCfgAccessListInputRuleEnable OBJECT-TYPE
        SYNTAX       INTEGER { invalid(0), disable(1), enable(2) }
        MAX-ACCESS   read-write
        STATUS       current
        DESCRIPTION  "IP Access Control Input Filter Rule"
        ::= { ipeCfgAccessListRuleEntry 3 }

    ipeCfgAccessListForwardRuleEnable OBJECT-TYPE
        SYNTAX       INTEGER { invalid(0), disable(1), enable(2) }
        MAX-ACCESS   read-write
        STATUS       current
        DESCRIPTION  "IP Access Control Forwarding Filter Rule"
        ::= { ipeCfgAccessListRuleEntry 4 }

    ipeCfgAccessListInputDefaultAction OBJECT-TYPE
        SYNTAX       INTEGER { permit(1), deny(2) }
        MAX-ACCESS   read-write
        STATUS       current
        DESCRIPTION  "IP Access Control Input Default Action."
        ::= { ipeCfgAccessListRuleEntry 5 }

    ipeCfgAccessListForwardDefaultAction OBJECT-TYPE
        SYNTAX       INTEGER { permit(1), deny(2) }
        MAX-ACCESS   read-write
        STATUS       current
        DESCRIPTION  "IP Access Control Forwarding Default Action"
        ::= { ipeCfgAccessListRuleEntry 6 }

    ipeCfgAccessListV6InputRuleEnable OBJECT-TYPE
        SYNTAX       INTEGER { invalid(0), disable(1), enable(2) }
        MAX-ACCESS   read-write
        STATUS       current
        DESCRIPTION  "IPv6 Access Control Input Filter Rule"
        ::= { ipeCfgAccessListRuleEntry 7 }

    ipeCfgAccessListV6ForwardRuleEnable OBJECT-TYPE
        SYNTAX       INTEGER { invalid(0), disable(1), enable(2) }
        MAX-ACCESS   read-write
        STATUS       current
        DESCRIPTION  "IPv6 Access Control Forwarding Filter Rule"
        ::= { ipeCfgAccessListRuleEntry 8 }

    ipeCfgAccessListV6InputDefaultAction OBJECT-TYPE
        SYNTAX       INTEGER { permit(1), deny(2) }
        MAX-ACCESS   read-write
        STATUS       current
        DESCRIPTION  "IPv6 Access Control Input Default Action."
        ::= { ipeCfgAccessListRuleEntry 9 }

    ipeCfgAccessListV6ForwardDefaultAction OBJECT-TYPE
        SYNTAX       INTEGER { permit(1), deny(2) }
        MAX-ACCESS   read-write
        STATUS       current
        DESCRIPTION  "IPv6 Access Control Forwarding Default Action"
        ::= { ipeCfgAccessListRuleEntry 10 }

    ipeCfgAccessListInputTable OBJECT-TYPE
        SYNTAX       SEQUENCE OF IpeCfgAccessListInputEntry
        MAX-ACCESS   not-accessible
        STATUS       current
        DESCRIPTION  "Table of Access List(Input Direction)."
        ::= { ipeCfgAccessListGroup 2 }

    ipeCfgAccessListInputEntry OBJECT-TYPE
        SYNTAX       IpeCfgAccessListInputEntry
        MAX-ACCESS   not-accessible
        STATUS       current
        DESCRIPTION  "Entry of Access List(Input Direction)."
        INDEX        { ipeCfgAccessListInputOrderNum }
        ::= { ipeCfgAccessListInputTable 1 }

    IpeCfgAccessListInputEntry ::= SEQUENCE {
        ipeCfgAccessListInputOrderNum      Integer32,
        ipeCfgAccessListInputNEAddress     IpAddress,
        ipeCfgAccessListInputInIfIndex     INTEGER,
        ipeCfgAccessListInputSrcIpAddress  IpAddress,
        ipeCfgAccessListInputSrcNetMask    IpAddress,
        ipeCfgAccessListInputProtocol      Integer32,
        ipeCfgAccessListInputDstPortNum    Integer32,
        ipeCfgAccessListInputAction        INTEGER,
        ipeCfgAccessListInputRowStatus     RowStatus
    }

    ipeCfgAccessListInputOrderNum OBJECT-TYPE
        SYNTAX       Integer32 (1..50)
        MAX-ACCESS   not-accessible
        STATUS       current
        DESCRIPTION  "Index of table(1-50)."
        ::= { ipeCfgAccessListInputEntry 1 }

    ipeCfgAccessListInputNEAddress OBJECT-TYPE
        SYNTAX       IpAddress
        MAX-ACCESS   not-accessible
        STATUS       current
        DESCRIPTION  ""
        ::= { ipeCfgAccessListInputEntry 2 }

    ipeCfgAccessListInputInIfIndex OBJECT-TYPE
        SYNTAX       INTEGER {
                         any(0),
                         lct(2),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "IP Access Control Input Filter Interface.
            The value 'inband' and 'ne2' are not supported."
        ::= { ipeCfgAccessListInputEntry 3 }

    ipeCfgAccessListInputSrcIpAddress OBJECT-TYPE
        SYNTAX       IpAddress
        MAX-ACCESS   read-create
        STATUS       current
        DESCRIPTION  "IP Access Control Input Filter Source IP Address"
        ::= { ipeCfgAccessListInputEntry 4 }

    ipeCfgAccessListInputSrcNetMask OBJECT-TYPE
        SYNTAX       IpAddress
        MAX-ACCESS   read-create
        STATUS       current
        DESCRIPTION  
            "IP Access Control Input Filter Source Subnet Mask.
            '0.0.0.0' matches all IP addresses. i.e. '0.0.0.0' acts as
            'Any'."
        ::= { ipeCfgAccessListInputEntry 5 }

    ipeCfgAccessListInputProtocol OBJECT-TYPE
        SYNTAX       Integer32
        MAX-ACCESS   read-create
        STATUS       current
        DESCRIPTION  
            "IP Access Control Input Filter Protocol.
            '-1' acts as 'Any'."
        ::= { ipeCfgAccessListInputEntry 6 }

    ipeCfgAccessListInputDstPortNum OBJECT-TYPE
        SYNTAX       Integer32
        MAX-ACCESS   read-create
        STATUS       current
        DESCRIPTION  
            "IP Access Control Input Filter Port Number.
            '-1' acts as 'Any'."
        ::= { ipeCfgAccessListInputEntry 7 }

    ipeCfgAccessListInputAction OBJECT-TYPE
        SYNTAX       INTEGER { permit(1), deny(2) }
        MAX-ACCESS   read-create
        STATUS       current
        DESCRIPTION  "IP Access Control Input Filter Action."
        ::= { ipeCfgAccessListInputEntry 8 }

    ipeCfgAccessListInputRowStatus OBJECT-TYPE
        SYNTAX       RowStatus { active(1), createAndGo(4), destroy(6) }
        MAX-ACCESS   read-create
        STATUS       current
        DESCRIPTION  
            "This RowStatus has a status only 'active(1)'. 
            
            1) creating a entry
            When you make a new entry, you must SET objects indicated below.
            ipeCfgAccessListInputAction
            ipeCfgAccessListInputRowStatus <- createAndGo(4)
            
            
            When you are not setting a value of items as follows, it is set
            as 'any'.
            ipeCfgAccessListInputInIfIndex
            ipeCfgAccessListInputSrcIpAddress
            ipeCfgAccessListInputSrcNetMask(*1)
            ipeCfgAccessListInputProtocol
            ipeCfgAccessListInputDstPortNum(*2)
            
            *1 When you not set ipeCfgAccessListInputSrcIpAddress, even when
            ipeCfgAccessListInputSrcNetMask is set, it is set as 'any'.When
            ipeCfgAccessListInputSrcIpAddress set to 'any',
            ipeCfgAccessListInputSrcNetMask is set as 'any'.
            *2 When you not set ipeCfgAccessListInputProtocol to '6' or '17',
            even when ipeCfgAccessListInputDstPortNum is set, it is set as
            'any'.
            
            2) modifing a entry
            It isn't possible.
            
            3) deleting a entry
            When you SET a destroy(6) to ipeCfgAccessListInputRowStatus, the
            entry is destroyed."
        ::= { ipeCfgAccessListInputEntry 9 }

    ipeCfgAccessListForwardTable OBJECT-TYPE
        SYNTAX       SEQUENCE OF IpeCfgAccessListForwardEntry
        MAX-ACCESS   not-accessible
        STATUS       current
        DESCRIPTION  "Table of Access List(Forward Direction)."
        ::= { ipeCfgAccessListGroup 3 }

    ipeCfgAccessListForwardEntry OBJECT-TYPE
        SYNTAX       IpeCfgAccessListForwardEntry
        MAX-ACCESS   not-accessible
        STATUS       current
        DESCRIPTION  "Entry of Access List(Forward Direction)."
        INDEX        { ipeCfgAccessListForwardOrderNum }
        ::= { ipeCfgAccessListForwardTable 1 }

    IpeCfgAccessListForwardEntry ::= SEQUENCE {
        ipeCfgAccessListForwardOrderNum      Integer32,
        ipeCfgAccessListForwardNEAddress     IpAddress,
        ipeCfgAccessListForwardInIfIndex     INTEGER,
        ipeCfgAccessListForwardOutIfIndex    INTEGER,
        ipeCfgAccessListForwardSrcIpAddress  IpAddress,
        ipeCfgAccessListForwardSrcNetMask    IpAddress,
        ipeCfgAccessListForwardDstIpAddress  IpAddress,
        ipeCfgAccessListForwardDstNetMask    IpAddress,
        ipeCfgAccessListForwardProtocol      Integer32,
        ipeCfgAccessListForwardSrcPortNum    Integer32,
        ipeCfgAccessListForwardDstPortNum    Integer32,
        ipeCfgAccessListForwardAction        INTEGER,
        ipeCfgAccessListForwardRowStatus     RowStatus
    }

    ipeCfgAccessListForwardOrderNum OBJECT-TYPE
        SYNTAX       Integer32 (1..50)
        MAX-ACCESS   not-accessible
        STATUS       current
        DESCRIPTION  "Index of table(1-50)."
        ::= { ipeCfgAccessListForwardEntry 1 }

    ipeCfgAccessListForwardNEAddress OBJECT-TYPE
        SYNTAX       IpAddress
        MAX-ACCESS   not-accessible
        STATUS       current
        DESCRIPTION  ""
        ::= { ipeCfgAccessListForwardEntry 2 }

    ipeCfgAccessListForwardInIfIndex OBJECT-TYPE
        SYNTAX       INTEGER {
                         any(0),
                         lct(2),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "IP Access Control Forward Filter Input Interface.
            
            The value 'inband' and 'ne2' are not supported."
        ::= { ipeCfgAccessListForwardEntry 3 }

    ipeCfgAccessListForwardOutIfIndex OBJECT-TYPE
        SYNTAX       INTEGER {
                         any(0),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "IP Access Control Forward Filter Output Interface.
            
            The value 'inband' and 'ne2' is not supported."
        ::= { ipeCfgAccessListForwardEntry 4 }

    ipeCfgAccessListForwardSrcIpAddress OBJECT-TYPE
        SYNTAX       IpAddress
        MAX-ACCESS   read-create
        STATUS       current
        DESCRIPTION  "IP Access Control Forward Filter Source IP Address."
        ::= { ipeCfgAccessListForwardEntry 5 }

    ipeCfgAccessListForwardSrcNetMask OBJECT-TYPE
        SYNTAX       IpAddress
        MAX-ACCESS   read-create
        STATUS       current
        DESCRIPTION  
            "IP Access Control Forward Filter Source Subnet Mask.
            '0.0.0.0' matches all IP addresses. i.e. '0.0.0.0' acts as 'Any'"
        ::= { ipeCfgAccessListForwardEntry 6 }

    ipeCfgAccessListForwardDstIpAddress OBJECT-TYPE
        SYNTAX       IpAddress
        MAX-ACCESS   read-create
        STATUS       current
        DESCRIPTION  
            "IP Access Control Forward Filter Destination IP Address."
        ::= { ipeCfgAccessListForwardEntry 7 }

    ipeCfgAccessListForwardDstNetMask OBJECT-TYPE
        SYNTAX       IpAddress
        MAX-ACCESS   read-create
        STATUS       current
        DESCRIPTION  
            "IP Access Control Forward Filter Destination Subnet Mask.
            '0.0.0.0' matches all IP addresses. i.e. '0.0.0.0' acts as
            'Any'."
        ::= { ipeCfgAccessListForwardEntry 8 }

    ipeCfgAccessListForwardProtocol OBJECT-TYPE
        SYNTAX       Integer32
        MAX-ACCESS   read-create
        STATUS       current
        DESCRIPTION  
            "IP Access Control Forward Filter Protocol.
            '-1' acts as 'Any'."
        ::= { ipeCfgAccessListForwardEntry 9 }

    ipeCfgAccessListForwardSrcPortNum OBJECT-TYPE
        SYNTAX       Integer32
        MAX-ACCESS   read-create
        STATUS       current
        DESCRIPTION  
            "IP Access Control Forward Filter Source Port Number.
            '-1' acts as 'Any'."
        ::= { ipeCfgAccessListForwardEntry 10 }

    ipeCfgAccessListForwardDstPortNum OBJECT-TYPE
        SYNTAX       Integer32
        MAX-ACCESS   read-create
        STATUS       current
        DESCRIPTION  
            "IP Access Control Forward Filter Destination Port Number.
            '-1' acts as 'Any'."
        ::= { ipeCfgAccessListForwardEntry 11 }

    ipeCfgAccessListForwardAction OBJECT-TYPE
        SYNTAX       INTEGER { permit(1), deny(2) }
        MAX-ACCESS   read-create
        STATUS       current
        DESCRIPTION  "IP Access Control Forward Filter Action."
        ::= { ipeCfgAccessListForwardEntry 12 }

    ipeCfgAccessListForwardRowStatus OBJECT-TYPE
        SYNTAX       RowStatus { active(1), createAndGo(4), destroy(6) }
        MAX-ACCESS   read-create
        STATUS       current
        DESCRIPTION  
            "This RowStatus has a status only 'active(1)'. 
            
            1) creating a entry
            When you make a new entry, you must SET objects indicated below.
            ipeCfgAccessListForwardAction
            ipeCfgAccessListForwardRowStatus <- createAndGo(4)
            
            
            When you are not setting a value of items as follows, it is set
            as 'any'.
            ipeCfgAccessListForwardInIfIndex
            ipeCfgAccessListForwardOutIfIndex
            ipeCfgAccessListForwardSrcIpAddress
            ipeCfgAccessListForwardSrcNetMask(*1)
            ipeCfgAccessListForwardDstIpAddress
            ipeCfgAccessListForwardDstNetMask(*2)
            ipeCfgAccessListForwardProtocol
            ipeCfgAccessListForwardSrcPortNum(*3)
            ipeCfgAccessListForwardDstPortNum(*3)
            
            *1 When you not set ipeCfgAccessListForwardSrcIpAddress, even
            when ipeCfgAccessListForwardSrcNetMask is set, it is set as
            'any'.When ipeCfgAccessListForwardSrcIpAddress set to 'any',
            ipeCfgAccessListForwardSrcNetMask is set as 'any'.
            *2 When you not set ipeCfgAccessListForwardDstIpAddress, even
            when ipeCfgAccessListForwardDstNetMask is set, it is set as
            'any'.When ipeCfgAccessListForwardDstIpAddress set to 'any',
            ipeCfgAccessListForwardDstNetMask is set as 'any'.
            *3 When you not set ipeCfgAccessListForwardProtocol to '6' or
            '17',, even when ipeCfgAccessListForwardSrcPortNum and
            ipeCfgAccessListForwardDstPortNum are set, it is set as 'any'.
            
            2) modifing a entry
            It isn't possible.
            
            3) deleting a entry
            When you SET a destroy(6) to ipeCfgAccessListForwardRowStatus,
            the entry is destroyed."
        ::= { ipeCfgAccessListForwardEntry 13 }

    ipeCfgAccessListV6InputTable OBJECT-TYPE
        SYNTAX       SEQUENCE OF IpeCfgAccessListV6InputEntry
        MAX-ACCESS   not-accessible
        STATUS       current
        DESCRIPTION  "Table of Access List(Input Direction)."
        ::= { ipeCfgAccessListGroup 4 }

    ipeCfgAccessListV6InputEntry OBJECT-TYPE
        SYNTAX       IpeCfgAccessListV6InputEntry
        MAX-ACCESS   not-accessible
        STATUS       current
        DESCRIPTION  ""
        INDEX        { ipeCfgAccessListV6InputOrder }
        ::= { ipeCfgAccessListV6InputTable 1 }

    IpeCfgAccessListV6InputEntry ::= SEQUENCE {
        ipeCfgAccessListV6InputOrder         Integer32,
        ipeCfgAccessListV6InputNEAddress     IpAddress,
        ipeCfgAccessListV6InputInIfIndex     INTEGER,
        ipeCfgAccessListV6InputSrcIpAddress  Ipv6Address,
        ipeCfgAccessListV6InputSrcPrefixLen  InetAddressPrefixLength,
        ipeCfgAccessListV6InputProtocol      Integer32,
        ipeCfgAccessListV6InputDstPort       Integer32,
        ipeCfgAccessListV6InputAction        INTEGER,
        ipeCfgAccessListV6InputRowStatus     RowStatus
    }

    ipeCfgAccessListV6InputOrder OBJECT-TYPE
        SYNTAX       Integer32 (1..50)
        MAX-ACCESS   not-accessible
        STATUS       current
        DESCRIPTION  "Index of this table."
        ::= { ipeCfgAccessListV6InputEntry 1 }

    ipeCfgAccessListV6InputNEAddress OBJECT-TYPE
        SYNTAX       IpAddress
        MAX-ACCESS   not-accessible
        STATUS       current
        DESCRIPTION  "reserved"
        ::= { ipeCfgAccessListV6InputEntry 2 }

    ipeCfgAccessListV6InputInIfIndex OBJECT-TYPE
        SYNTAX       INTEGER {
                         any(0),
                         lct(2),
                         inband(3),
                         ne2(4),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "IP Access Control Input Filter Interface.
            
            The value 'inband' and 'ne2' are not supported."
        ::= { ipeCfgAccessListV6InputEntry 3 }

    ipeCfgAccessListV6InputSrcIpAddress OBJECT-TYPE
        SYNTAX       Ipv6Address
        MAX-ACCESS   read-create
        STATUS       current
        DESCRIPTION  "IP Access Control Input Filter Source IP Address"
        ::= { ipeCfgAccessListV6InputEntry 4 }

    ipeCfgAccessListV6InputSrcPrefixLen OBJECT-TYPE
        SYNTAX       InetAddressPrefixLength
        MAX-ACCESS   read-create
        STATUS       current
        DESCRIPTION  
            "IP Access Control Input Filter Source Prefix Length.
            '0' matches all IP addresses. i.e. '0' acts as 'Any'."
        ::= { ipeCfgAccessListV6InputEntry 5 }

    ipeCfgAccessListV6InputProtocol OBJECT-TYPE
        SYNTAX       Integer32
        MAX-ACCESS   read-create
        STATUS       current
        DESCRIPTION  
            "IP Access Control Input Filter Protocol.
            '-1' acts as 'Any'."
        ::= { ipeCfgAccessListV6InputEntry 6 }

    ipeCfgAccessListV6InputDstPort OBJECT-TYPE
        SYNTAX       Integer32
        MAX-ACCESS   read-create
        STATUS       current
        DESCRIPTION  
            "IP Access Control Input Filter Port Number.
            '-1' acts as 'Any'."
        ::= { ipeCfgAccessListV6InputEntry 7 }

    ipeCfgAccessListV6InputAction OBJECT-TYPE
        SYNTAX       INTEGER { permit(1), deny(2) }
        MAX-ACCESS   read-create
        STATUS       current
        DESCRIPTION  "IP Access Control Input Filter Action."
        ::= { ipeCfgAccessListV6InputEntry 8 }

    ipeCfgAccessListV6InputRowStatus OBJECT-TYPE
        SYNTAX       RowStatus
        MAX-ACCESS   read-create
        STATUS       current
        DESCRIPTION  
            "This RowStatus has a status only 'active(1)'. 
            
            1) creating a entry
            When you make a new entry, you must SET objects indicated below.
            ipeCfgAccessListV6InputAction
            ipeCfgAccessListV6InputRowStatus <- createAndGo(4)
            
            
            When you are not setting a value of items as follows, it is set
            as 'any'.
            ipeCfgAccessListV6InputInIfIndex
            ipeCfgAccessListV6InputSrcIpAddress
            ipeCfgAccessListV6InputSrcPrefixLength(*1)
            ipeCfgAccessListV6InputProtocol
            ipeCfgAccessListV6InputDstPortNum(*2)
            
            *1 When you not set ipeCfgAccessListInputSrcIpAddress, even when
            ipeCfgAccessListV6InputSrcPrefixLength is set, it is set as
            'any'. When ipeCfgAccessListV6InputSrcIpAddress set to 'any',
            ipeCfgAccessListV6InputSrcPrefixLength is set as 'any'.
            *2 When you not set ipeCfgAccessListV6InputProtocol to '6' or
            '17', even when ipeCfgAccessListV6InputDstPortNum is set, it is
            set as 'any'.
            
            2) modifing a entry
            It isn't possible.
            
            3) deleting a entry
            When you SET a destroy(6) to ipeCfgAccessListV6InputRowStatus,
            the entry is destroyed."
        ::= { ipeCfgAccessListV6InputEntry 9 }

    ipeCfgAccessListV6ForwardTable OBJECT-TYPE
        SYNTAX       SEQUENCE OF IpeCfgAccessListV6ForwardEntry
        MAX-ACCESS   not-accessible
        STATUS       current
        DESCRIPTION  "Table of Access List(Forward Direction)."
        ::= { ipeCfgAccessListGroup 5 }

    ipeCfgAccessListV6ForwardEntry OBJECT-TYPE
        SYNTAX       IpeCfgAccessListV6ForwardEntry
        MAX-ACCESS   not-accessible
        STATUS       current
        DESCRIPTION  ""
        INDEX        { ipeCfgAccessListV6ForwardOrder }
        ::= { ipeCfgAccessListV6ForwardTable 1 }

    IpeCfgAccessListV6ForwardEntry ::= SEQUENCE {
        ipeCfgAccessListV6ForwardOrder         Integer32,
        ipeCfgAccessListV6ForwardNEAddress     IpAddress,
        ipeCfgAccessListV6ForwardInIfIndex     INTEGER,
        ipeCfgAccessListV6ForwardOutIfIndex    INTEGER,
        ipeCfgAccessListV6ForwardSrcIpAddress  Ipv6Address,
        ipeCfgAccessListV6ForwardSrcPrefixLen  InetAddressPrefixLength,
        ipeCfgAccessListV6ForwardDstIpAddress  Ipv6Address,
        ipeCfgAccessListV6ForwardDstPrefixLen  InetAddressPrefixLength,
        ipeCfgAccessListV6ForwardProtocol      Integer32,
        ipeCfgAccessListV6ForwardSrcPort       Integer32,
        ipeCfgAccessListV6ForwardDstPort       Integer32,
        ipeCfgAccessListV6ForwardAction        INTEGER,
        ipeCfgAccessListV6ForwardRowStatus     RowStatus
    }

    ipeCfgAccessListV6ForwardOrder OBJECT-TYPE
        SYNTAX       Integer32 (1..50)
        MAX-ACCESS   not-accessible
        STATUS       current
        DESCRIPTION  "Index of this table"
        ::= { ipeCfgAccessListV6ForwardEntry 1 }

    ipeCfgAccessListV6ForwardNEAddress OBJECT-TYPE
        SYNTAX       IpAddress
        MAX-ACCESS   not-accessible
        STATUS       current
        DESCRIPTION  "reserved"
        ::= { ipeCfgAccessListV6ForwardEntry 2 }

    ipeCfgAccessListV6ForwardInIfIndex OBJECT-TYPE
        SYNTAX       INTEGER {
                         any(0),
                         lct(2),
                         inband(3),
                         ne2(4),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "IP Access Control Forward Filter Input Interface.
            
            The value 'inband' and 'ne2' are not supported."
        ::= { ipeCfgAccessListV6ForwardEntry 3 }

    ipeCfgAccessListV6ForwardOutIfIndex OBJECT-TYPE
        SYNTAX       INTEGER {
                         any(0),
                         lct(2),
                         inband(3),
                         ne2(4),
                         bridge1(11),
                         bridge2(12),
                         bridge3(13),
                         bridge4(14),
                         bridge5(15),
                         bridge6(16),
                         bridge7(17),
                         bridge8(18),
                         bridge9(19),
                         bridge10(20),
                         bridge11(21),
                         bridge12(22),
                         bridge13(23),
                         bridge14(24),
                         bridge15(25),
                         bridge16(26),
                         bridge17(27),
                         bridge18(28),
                         bridge19(29),
                         bridge20(30)
                     }
        MAX-ACCESS   read-create
        STATUS       current
        DESCRIPTION  
            "IP Access Control Forward Filter Input Interface.
            
            The value 'inband' and 'ne2' are not supported."
        ::= { ipeCfgAccessListV6ForwardEntry 4 }

    ipeCfgAccessListV6ForwardSrcIpAddress OBJECT-TYPE
        SYNTAX       Ipv6Address
        MAX-ACCESS   read-create
        STATUS       current
        DESCRIPTION  "IP Access Control Forward Filter Source IP Address."
        ::= { ipeCfgAccessListV6ForwardEntry 5 }

    ipeCfgAccessListV6ForwardSrcPrefixLen OBJECT-TYPE
        SYNTAX       InetAddressPrefixLength
        MAX-ACCESS   read-create
        STATUS       current
        DESCRIPTION  
            "IP Access Control Forward Filter Destination Prefix Length.
            '0' matches all IP addresses. i.e. '0' acts as 'Any'."
        ::= { ipeCfgAccessListV6ForwardEntry 6 }

    ipeCfgAccessListV6ForwardDstIpAddress OBJECT-TYPE
        SYNTAX       Ipv6Address
        MAX-ACCESS   read-create
        STATUS       current
        DESCRIPTION  
            "IP Access Control Forward Filter Destination IP Address."
        ::= { ipeCfgAccessListV6ForwardEntry 7 }

    ipeCfgAccessListV6ForwardDstPrefixLen OBJECT-TYPE
        SYNTAX       InetAddressPrefixLength
        MAX-ACCESS   read-create
        STATUS       current
        DESCRIPTION  
            "IP Access Control Forward Filter Destination Prefix Length.
            '0' matches all IP addresses. i.e. '0' acts as 'Any'."
        ::= { ipeCfgAccessListV6ForwardEntry 8 }

    ipeCfgAccessListV6ForwardProtocol OBJECT-TYPE
        SYNTAX       Integer32
        MAX-ACCESS   read-create
        STATUS       current
        DESCRIPTION  
            "IP Access Control Forward Filter Protocol.
            '-1' acts as 'Any'."
        ::= { ipeCfgAccessListV6ForwardEntry 9 }

    ipeCfgAccessListV6ForwardSrcPort OBJECT-TYPE
        SYNTAX       Integer32
        MAX-ACCESS   read-create
        STATUS       current
        DESCRIPTION  
            "IP Access Control Forward Filter Source Port Number.
            '-1' acts as 'Any'."
        ::= { ipeCfgAccessListV6ForwardEntry 10 }

    ipeCfgAccessListV6ForwardDstPort OBJECT-TYPE
        SYNTAX       Integer32
        MAX-ACCESS   read-create
        STATUS       current
        DESCRIPTION  
            "IP Access Control Forward Filter Destination Port Number.
            '-1' acts as 'Any'."
        ::= { ipeCfgAccessListV6ForwardEntry 11 }

    ipeCfgAccessListV6ForwardAction OBJECT-TYPE
        SYNTAX       INTEGER { permit(1), deny(2) }
        MAX-ACCESS   read-create
        STATUS       current
        DESCRIPTION  "IP Access Control Forward Filter Action."
        ::= { ipeCfgAccessListV6ForwardEntry 12 }

    ipeCfgAccessListV6ForwardRowStatus OBJECT-TYPE
        SYNTAX       RowStatus
        MAX-ACCESS   read-create
        STATUS       current
        DESCRIPTION  
            "This RowStatus has a status only 'active(1)'. 
            
            1) creating a entry
            When you make a new entry, you must SET objects indicated below.
            ipeCfgAccessListV6ForwardAction
            ipeCfgAccessListV6ForwardRowStatus <- createAndGo(4)
            
            
            When you are not setting a value of items as follows, it is set
            as 'any'.
            ipeCfgAccessListV6ForwardInIfIndex
            ipeCfgAccessListV6ForwardOutIfIndex
            ipeCfgAccessListV6ForwardSrcIpAddress
            ipeCfgAccessListV6ForwardSrcPrefixLength(*1)
            ipeCfgAccessListV6ForwardDstIpAddress
            ipeCfgAccessListV6ForwardDstPrefixLength(*2)
            ipeCfgAccessListV6ForwardProtocol
            ipeCfgAccessListV6ForwardSrcPortNum(*3)
            ipeCfgAccessListV6ForwardDstPortNum(*3)
            
            *1 When you not set ipeCfgAccessListV6ForwardSrcIpAddress, even
            when ipeCfgAccessListV6ForwardSrcPrefixLength is set, it is set
            as 'any'. When ipeCfgAccessListV6ForwardSrcIpAddress set to
            'any', ipeCfgAccessListV6ForwardSrcPrefixLength is set as 'any'.
            *2 When you not set ipeCfgAccessListV6ForwardDstIpAddress, even
            when ipeCfgAccessListV6ForwardDstPrefixLength is set, it is set
            as 'any'. When ipeCfgAccessListV6ForwardDstIpAddress set to
            'any', ipeCfgAccessListV6ForwardDstPrefixLength is set as 'any'.
            *3 When you not set ipeCfgAccessListV6ForwardProtocol to '6' or
            '17', even when ipeCfgAccessListV6ForwardSrcPortNum and
            ipeCfgAccessListV6ForwardDstPortNum are set, it is set as 'any'.
            
            2) modifing a entry
            It isn't possible.
            
            3) deleting a entry
            When you SET a destroy(6) to ipeCfgAccessListV6ForwardRowStatus,
            the entry is destroyed."
        ::= { ipeCfgAccessListV6ForwardEntry 13 }

    ipeCfgAccessListDSCPTable OBJECT-TYPE
        SYNTAX       SEQUENCE OF IpeCfgAccessListDSCPEntry
        MAX-ACCESS   not-accessible
        STATUS       current
        DESCRIPTION  "Table of DSCP configuration information."
        ::= { ipeCfgAccessListGroup 6 }

    ipeCfgAccessListDSCPEntry OBJECT-TYPE
        SYNTAX       IpeCfgAccessListDSCPEntry
        MAX-ACCESS   not-accessible
        STATUS       current
        DESCRIPTION  "Entry of DSCP configuration information."
        INDEX        { ipeCfgAccessListDSCPIndex }
        ::= { ipeCfgAccessListDSCPTable 1 }

    IpeCfgAccessListDSCPEntry ::= SEQUENCE {
        ipeCfgAccessListDSCPIndex      Integer32,
        ipeCfgAccessListDSCPNEAddress  IpAddress,
        ipeCfgAccessListDSCPValue      Integer32
    }

    ipeCfgAccessListDSCPIndex OBJECT-TYPE
        SYNTAX       Integer32 (1..1)
        MAX-ACCESS   not-accessible
        STATUS       current
        DESCRIPTION  "Index of this table. Only one instance is created."
        ::= { ipeCfgAccessListDSCPEntry 1 }

    ipeCfgAccessListDSCPNEAddress OBJECT-TYPE
        SYNTAX       IpAddress
        MAX-ACCESS   not-accessible
        STATUS       current
        DESCRIPTION  "reserved"
        ::= { ipeCfgAccessListDSCPEntry 2 }

    ipeCfgAccessListDSCPValue OBJECT-TYPE
        SYNTAX       Integer32 (0..63)
        MAX-ACCESS   read-write
        STATUS       current
        DESCRIPTION  
            "Indicates the DSCP value for the outgoing/forwarding packets
            from Bridge/LCT Interface in equipment unit."
        ::= { ipeCfgAccessListDSCPEntry 3 }

    ipeCfgAutoIpGroup OBJECT IDENTIFIER
        ::= { ipeConfigurationGroup 22 }

    ipeCfgAutoIpTable OBJECT-TYPE
        SYNTAX       SEQUENCE OF IpeCfgAutoIpEntry
        MAX-ACCESS   not-accessible
        STATUS       current
        DESCRIPTION  "Table of AutoIP configuration information."
        ::= { ipeCfgAutoIpGroup 1 }

    ipeCfgAutoIpEntry OBJECT-TYPE
        SYNTAX       IpeCfgAutoIpEntry
        MAX-ACCESS   not-accessible
        STATUS       current
        DESCRIPTION  "Entry of AutoIP configuration information."
        INDEX        { ipeCfgAutoIpIndex }
        ::= { ipeCfgAutoIpTable 1 }

    IpeCfgAutoIpEntry ::= SEQUENCE {
        ipeCfgAutoIpIndex           Integer32,
        ipeCfgAutoIpNEAddress       IpAddress,
        ipeCfgAutoIpNetworkAddress  IpAddress,
        ipeCfgAutoIpNetMask         IpAddress
    }

    ipeCfgAutoIpIndex OBJECT-TYPE
        SYNTAX       Integer32 (1..1)
        MAX-ACCESS   not-accessible
        STATUS       current
        DESCRIPTION  
            "Index of table.
            It's a fixed value(=1)."
        ::= { ipeCfgAutoIpEntry 1 }

    ipeCfgAutoIpNEAddress OBJECT-TYPE
        SYNTAX       IpAddress
        MAX-ACCESS   not-accessible
        STATUS       current
        DESCRIPTION  ""
        ::= { ipeCfgAutoIpEntry 2 }

    ipeCfgAutoIpNetworkAddress OBJECT-TYPE
        SYNTAX       IpAddress
        MAX-ACCESS   read-write
        STATUS       current
        DESCRIPTION  
            "Aggregation Net of AutoIP.
            A set value becomes a binary.
            Value range:0x00000000-0xdfffffff(0.0.0.0-223.255.255.255)
            If this value is changed in state of 'now setting' or 'automatic
            setting', AutoIP will set IP Address again."
        ::= { ipeCfgAutoIpEntry 3 }

    ipeCfgAutoIpNetMask OBJECT-TYPE
        SYNTAX       IpAddress
        MAX-ACCESS   read-write
        STATUS       current
        DESCRIPTION  
            "Aggregation NetMask of AutoIp.
            A set value becomes a binary.
            Value range:0x80000000-0xfffffffc(1-30bit)
            If this value is changed in state of 'now setting' or 'automatic
            setting', AutoIP will set IP Address again."
        ::= { ipeCfgAutoIpEntry 4 }

    ipeCfgSysNE1PortTable OBJECT-TYPE
        SYNTAX       SEQUENCE OF IpeCfgSysNE1PortEntry
        MAX-ACCESS   not-accessible
        STATUS       current
        DESCRIPTION  "NE1 Port Mode Configuration Table."
        ::= { ipeConfigurationGroup 25 }

    ipeCfgSysNE1PortEntry OBJECT-TYPE
        SYNTAX       IpeCfgSysNE1PortEntry
        MAX-ACCESS   not-accessible
        STATUS       current
        DESCRIPTION  ""
        INDEX        { ipeCfgSysNE1PortIndex }
        ::= { ipeCfgSysNE1PortTable 1 }

    IpeCfgSysNE1PortEntry ::= SEQUENCE {
        ipeCfgSysNE1PortIndex      Integer32,
        ipeCfgSysNE1PortNEAddress  IpAddress,
        ipeCfgSysNE1PortMode       INTEGER
    }

    ipeCfgSysNE1PortIndex OBJECT-TYPE
        SYNTAX       Integer32 (1..1)
        MAX-ACCESS   not-accessible
        STATUS       current
        DESCRIPTION  "Index of this table."
        ::= { ipeCfgSysNE1PortEntry 1 }

    ipeCfgSysNE1PortNEAddress OBJECT-TYPE
        SYNTAX       IpAddress
        MAX-ACCESS   not-accessible
        STATUS       current
        DESCRIPTION  ""
        ::= { ipeCfgSysNE1PortEntry 2 }

    ipeCfgSysNE1PortMode OBJECT-TYPE
        SYNTAX       INTEGER { invalid(0), userPort(1), mgmtPort(2) }
        MAX-ACCESS   read-write
        STATUS       current
        DESCRIPTION  
            "NE1 Port Mode Configuration
            This value is not available [iPASOLINK EX Advanced]"
        DEFVAL       { userPort }
        ::= { ipeCfgSysNE1PortEntry 3 }

    ipeCfgRadiusGroup OBJECT IDENTIFIER
        ::= { ipeConfigurationGroup 27 }

    ipeCfgRadiusGeneralTable OBJECT-TYPE
        SYNTAX       SEQUENCE OF IpeCfgRadiusGeneralEntry
        MAX-ACCESS   not-accessible
        STATUS       current
        DESCRIPTION  "Configure RADIUS parameters."
        ::= { ipeCfgRadiusGroup 1 }

    ipeCfgRadiusGeneralEntry OBJECT-TYPE
        SYNTAX       IpeCfgRadiusGeneralEntry
        MAX-ACCESS   not-accessible
        STATUS       current
        DESCRIPTION  "..."
        INDEX        { ipeCfgRadiusGeneralIndex }
        ::= { ipeCfgRadiusGeneralTable 1 }

    IpeCfgRadiusGeneralEntry ::= SEQUENCE {
        ipeCfgRadiusGeneralIndex                 Integer32,
        ipeCfgRadiusGeneralNEAddress             IpAddress,
        ipeCfgRadiusGeneralAuthClientRetransmit  Integer32,
        ipeCfgRadiusGeneralAuthClientTimeout     Integer32
    }

    ipeCfgRadiusGeneralIndex OBJECT-TYPE
        SYNTAX       Integer32 (1..1)
        MAX-ACCESS   not-accessible
        STATUS       current
        DESCRIPTION  "The index of this table."
        ::= { ipeCfgRadiusGeneralEntry 1 }

    ipeCfgRadiusGeneralNEAddress OBJECT-TYPE
        SYNTAX       IpAddress
        MAX-ACCESS   not-accessible
        STATUS       current
        DESCRIPTION  "Reserved object for northbound interface."
        ::= { ipeCfgRadiusGeneralEntry 2 }

    ipeCfgRadiusGeneralAuthClientRetransmit OBJECT-TYPE
        SYNTAX       Integer32 (0..255)
        MAX-ACCESS   read-write
        STATUS       current
        DESCRIPTION  
            "Indicate maximum retransmit number of Access-Request
            message.
            The system retransmits Access-Request message to server
            according to this configuration."
        DEFVAL       { 3 }
        ::= { ipeCfgRadiusGeneralEntry 3 }

    ipeCfgRadiusGeneralAuthClientTimeout OBJECT-TYPE
        SYNTAX       Integer32 (0..65535)
        UNITS        "seconds"
        MAX-ACCESS   read-write
        STATUS       current
        DESCRIPTION  
            "Indicate timeout period for response to Access-Request
            message.
            In case response (Access-Accept message) is not received
            in this period, the system will retransmit message."
        DEFVAL       { 10 }
        ::= { ipeCfgRadiusGeneralEntry 4 }

    ipeCfgRadiusAuthServerExtTable OBJECT-TYPE
        SYNTAX       SEQUENCE OF IpeCfgRadiusAuthServerExtEntry
        MAX-ACCESS   not-accessible
        STATUS       current
        DESCRIPTION  "Configure RADIUS authentication server parameters."
        ::= { ipeCfgRadiusGroup 2 }

    ipeCfgRadiusAuthServerExtEntry OBJECT-TYPE
        SYNTAX       IpeCfgRadiusAuthServerExtEntry
        MAX-ACCESS   not-accessible
        STATUS       current
        DESCRIPTION  "..."
        INDEX        { ipeCfgRadiusAuthServerExtIndex }
        ::= { ipeCfgRadiusAuthServerExtTable 1 }

    IpeCfgRadiusAuthServerExtEntry ::= SEQUENCE {
        ipeCfgRadiusAuthServerExtIndex          Integer32,
        ipeCfgRadiusAuthServerNEAddress         IpAddress,
        ipeCfgRadiusAuthServerAddressType       INTEGER,
        ipeCfgRadiusAuthServerAddress           IpAddress,
        ipeCfgRadiusAuthClientServerPortNumber  Integer32,
        ipeCfgRadiusAuthClientPasswordType      INTEGER,
        ipeCfgRadiusAuthClientSecretKey         DisplayString,
        ipeCfgRadiusAuthServerExtRowStatus      RowStatus
    }

    ipeCfgRadiusAuthServerExtIndex OBJECT-TYPE
        SYNTAX       Integer32 (1..3)
        MAX-ACCESS   not-accessible
        STATUS       current
        DESCRIPTION  "The index of this table."
        ::= { ipeCfgRadiusAuthServerExtEntry 1 }

    ipeCfgRadiusAuthServerNEAddress OBJECT-TYPE
        SYNTAX       IpAddress
        MAX-ACCESS   not-accessible
        STATUS       current
        DESCRIPTION  "Reserved object for northbound interface."
        ::= { ipeCfgRadiusAuthServerExtEntry 2 }

    ipeCfgRadiusAuthServerAddressType OBJECT-TYPE
        SYNTAX       INTEGER { invalid(0), ipv4(1), ipv6(2) }
        MAX-ACCESS   read-create
        STATUS       current
        DESCRIPTION  
            "Indicate IP address type of this server.
            
            ipv4 : server has IPv4 address.
            ipv6 : server has IPv6 address. (NOT SUPPORTED)
            
            ipv6 will be supprted in future version."
        DEFVAL       { ipv4 }
        ::= { ipeCfgRadiusAuthServerExtEntry 3 }

    ipeCfgRadiusAuthServerAddress OBJECT-TYPE
        SYNTAX       IpAddress
        MAX-ACCESS   read-create
        STATUS       current
        DESCRIPTION  "Indicate IP address of this server."
        ::= { ipeCfgRadiusAuthServerExtEntry 4 }

    ipeCfgRadiusAuthClientServerPortNumber OBJECT-TYPE
        SYNTAX       Integer32 (0..65535)
        MAX-ACCESS   read-create
        STATUS       current
        DESCRIPTION  
            "Indicate port number of RADIUS authentication protocol on
            this server."
        DEFVAL       { 1812 }
        ::= { ipeCfgRadiusAuthServerExtEntry 5 }

    ipeCfgRadiusAuthClientPasswordType OBJECT-TYPE
        SYNTAX       INTEGER { invalid(0), user(1), chap(2) }
        MAX-ACCESS   read-create
        STATUS       current
        DESCRIPTION  
            "Indicate password authentication type. The system select
            password attribute on Access-Request message.
            
            user : use User-Password attribute.
            chap : use CHAP-Password attribute.
            
            See RFC 2865 for details."
        DEFVAL       { user }
        ::= { ipeCfgRadiusAuthServerExtEntry 6 }

    ipeCfgRadiusAuthClientSecretKey OBJECT-TYPE
        SYNTAX       DisplayString (SIZE(8..128))
        MAX-ACCESS   read-create
        STATUS       current
        DESCRIPTION  
            "Indicate RADIUS shared secret. This object can be operated only
            when in secure way. This object is used to confirm  received
            RADIUS message is
            sent from authenticated server.
            This object is also used to encrypt User-Password attribute
            on Access-Request message.
            See RFC 2865 for details.
            
            The secret key(before encryption) range is 1-63 characters."
        ::= { ipeCfgRadiusAuthServerExtEntry 7 }

    ipeCfgRadiusAuthServerExtRowStatus OBJECT-TYPE
        SYNTAX       RowStatus
        MAX-ACCESS   read-create
        STATUS       current
        DESCRIPTION  "The row status of this table."
        ::= { ipeCfgRadiusAuthServerExtEntry 8 }

    ipeCfgRadiusPrivLevelGeneralTable OBJECT-TYPE
        SYNTAX       SEQUENCE OF IpeCfgRadiusPrivLevelGeneralEntry
        MAX-ACCESS   not-accessible
        STATUS       current
        DESCRIPTION  
            "Configure general privilege level for RADIUS
            authetication."
        ::= { ipeCfgRadiusGroup 3 }

    ipeCfgRadiusPrivLevelGeneralEntry OBJECT-TYPE
        SYNTAX       IpeCfgRadiusPrivLevelGeneralEntry
        MAX-ACCESS   not-accessible
        STATUS       current
        DESCRIPTION  "..."
        INDEX        { ipeCfgRadiusPrivLevelGeneralIndex }
        ::= { ipeCfgRadiusPrivLevelGeneralTable 1 }

    IpeCfgRadiusPrivLevelGeneralEntry ::= SEQUENCE {
        ipeCfgRadiusPrivLevelGeneralIndex          Integer32,
        ipeCfgRadiusPrivLevelGeneralNEAddress      IpAddress,
        ipeCfgRadiusPrivLevelGeneralDefaultAction  INTEGER,
        ipeCfgRadiusPrivLevelGeneralDefaultGroup   DisplayString
    }

    ipeCfgRadiusPrivLevelGeneralIndex OBJECT-TYPE
        SYNTAX       Integer32 (1..1)
        MAX-ACCESS   not-accessible
        STATUS       current
        DESCRIPTION  "The index of this table."
        ::= { ipeCfgRadiusPrivLevelGeneralEntry 1 }

    ipeCfgRadiusPrivLevelGeneralNEAddress OBJECT-TYPE
        SYNTAX       IpAddress
        MAX-ACCESS   not-accessible
        STATUS       current
        DESCRIPTION  "Reserved object for northbound interface."
        ::= { ipeCfgRadiusPrivLevelGeneralEntry 2 }

    ipeCfgRadiusPrivLevelGeneralDefaultAction OBJECT-TYPE
        SYNTAX       INTEGER { invalid(0), denyLogin(1), useDefaultGroup(2) }
        MAX-ACCESS   read-write
        STATUS       current
        DESCRIPTION  
            "Indicate system default action in case privilege level
            is not specified on Access-Accept message or received
            privilege level is set to disable in 
            ipeCfgRadiusGroupPrivLevelMappingEnable.
            
            denyLogin       : deny login.
            useDefaultGroup : use group specified in
                              ipeCfgRadiusPrivLevelGeneralDefaultGroup."
        DEFVAL       { useDefaultGroup }
        ::= { ipeCfgRadiusPrivLevelGeneralEntry 3 }

    ipeCfgRadiusPrivLevelGeneralDefaultGroup OBJECT-TYPE
        SYNTAX       DisplayString (SIZE(1..32))
        MAX-ACCESS   read-write
        STATUS       current
        DESCRIPTION  
            "Indicate default group in case privilege level is not
            specified.
            This object is effective only if
            ipeCfgRadiusPrivLevelGeneralDefaultAction is
            useDefaultGroup.
            
            The value of this object should be registered group name in
            the system (as ipeCfgAccountGroupName).
            
            The characters which can be used are '-', '_','0'-'9', 
            'a'-'z' and 'A'-'Z'."
        DEFVAL       { "Operator" }
        ::= { ipeCfgRadiusPrivLevelGeneralEntry 4 }

    ipeCfgRadiusGroupPrivLevelMappingTable OBJECT-TYPE
        SYNTAX       SEQUENCE OF IpeCfgRadiusGroupPrivLevelMappingEntry
        MAX-ACCESS   not-accessible
        STATUS       current
        DESCRIPTION  
            "Configure privilege level mapping for RADIUS
            authentication."
        ::= { ipeCfgRadiusGroup 4 }

    ipeCfgRadiusGroupPrivLevelMappingEntry OBJECT-TYPE
        SYNTAX       IpeCfgRadiusGroupPrivLevelMappingEntry
        MAX-ACCESS   not-accessible
        STATUS       current
        DESCRIPTION  "..."
        INDEX        { ipeCfgRadiusGroupPrivLevelMappingPrivLevel }
        ::= { ipeCfgRadiusGroupPrivLevelMappingTable 1 }

    IpeCfgRadiusGroupPrivLevelMappingEntry ::= SEQUENCE {
        ipeCfgRadiusGroupPrivLevelMappingPrivLevel  Integer32,
        ipeCfgRadiusGroupPrivLevelMappingNEAddress  IpAddress,
        ipeCfgRadiusGroupPrivLevelMappingEnable     INTEGER,
        ipeCfgRadiusGroupPrivLevelMappingGroup      DisplayString
    }

    ipeCfgRadiusGroupPrivLevelMappingPrivLevel OBJECT-TYPE
        SYNTAX       Integer32 (0..15)
        MAX-ACCESS   not-accessible
        STATUS       current
        DESCRIPTION  
            "The index of this table.
            The value corresponds to received privilege level on
            Access-Accept message."
        ::= { ipeCfgRadiusGroupPrivLevelMappingEntry 1 }

    ipeCfgRadiusGroupPrivLevelMappingNEAddress OBJECT-TYPE
        SYNTAX       IpAddress
        MAX-ACCESS   not-accessible
        STATUS       current
        DESCRIPTION  "Reserved object for northbound interface."
        ::= { ipeCfgRadiusGroupPrivLevelMappingEntry 2 }

    ipeCfgRadiusGroupPrivLevelMappingEnable OBJECT-TYPE
        SYNTAX       INTEGER { invalid(0), disable(1), enable(2) }
        MAX-ACCESS   read-write
        STATUS       current
        DESCRIPTION  
            "Enable or disable privilege level mapping on this
            privilege level.
            
            disable : privilege level mapping is disabled.
            enable  : privilege level mapping is enabled.
            
            The system default value of this object shown below.
            
            PrivLevel=1, 7, 15 : enable
            other PrivLevel    : disable
            
            In case this object is set to disable, the system
            behave according to 
            ipeCfgRadiusPrivLevelGeneralDefaultAction."
        DEFVAL       { disable }
        ::= { ipeCfgRadiusGroupPrivLevelMappingEntry 3 }

    ipeCfgRadiusGroupPrivLevelMappingGroup OBJECT-TYPE
        SYNTAX       DisplayString (SIZE(1..32))
        MAX-ACCESS   read-write
        STATUS       current
        DESCRIPTION  
            "Indicate group name correspond to privilege level.
            This object is effective only if 
            ipeCfgRadiusGroupPrivLevelMappingEnable is enable.
            When the system received Access-Accept message with certain
            privilege level, login user has same privilege as this
            group.
            
            The system default value of this object shown below.
            
            PrivLevel=1  : Operator
            PrivLevel=7  : Config
            PrivLevel=15 : Admin
            
            The value should be registered group name registerd in
            the system (as ipeCfgAccountGroupName).
            The characters which can be used are '-', '_','0'-'9', 
            'a'-'z' and 'A'-'Z'."
        ::= { ipeCfgRadiusGroupPrivLevelMappingEntry 4 }

    ipeCfgLldpGroup OBJECT IDENTIFIER
        ::= { ipeConfigurationGroup 28 }

    ipeCfgLldpTable OBJECT-TYPE
        SYNTAX       SEQUENCE OF IpeCfgLldpEntry
        MAX-ACCESS   not-accessible
        STATUS       current
        DESCRIPTION  "LLDP set up information table."
        ::= { ipeCfgLldpGroup 1 }

    ipeCfgLldpEntry OBJECT-TYPE
        SYNTAX       IpeCfgLldpEntry
        MAX-ACCESS   not-accessible
        STATUS       current
        DESCRIPTION  "entry of LLDP set up information table."
        INDEX        { ipeCfgLldpIndex }
        ::= { ipeCfgLldpTable 1 }

    IpeCfgLldpEntry ::= SEQUENCE {
        ipeCfgLldpIndex                      Integer32,
        ipeCfgLldpNEAddress                  IpAddress,
        ipeCfgLldpProprietaryModeMacAddress  MacAddress
    }

    ipeCfgLldpIndex OBJECT-TYPE
        SYNTAX       Integer32 (1..1)
        MAX-ACCESS   not-accessible
        STATUS       current
        DESCRIPTION  "The index of this table."
        ::= { ipeCfgLldpEntry 1 }

    ipeCfgLldpNEAddress OBJECT-TYPE
        SYNTAX       IpAddress
        MAX-ACCESS   not-accessible
        STATUS       current
        DESCRIPTION  "reserved."
        ::= { ipeCfgLldpEntry 2 }

    ipeCfgLldpProprietaryModeMacAddress OBJECT-TYPE
        SYNTAX       MacAddress
        MAX-ACCESS   read-write
        STATUS       current
        DESCRIPTION  
            "MAC address of LLDP Frame in NEC mode.
            This object is effective only if ipeCfgPortXXXXXLldpMode is set
            to proprietaryMode."
        DEFVAL       { '01004c01da50'h }
        ::= { ipeCfgLldpEntry 3 }

    ipeCfgMgmtTrafficGrop OBJECT IDENTIFIER
        ::= { ipeConfigurationGroup 29 }

    ipeCfgMgmtTrafficControlTable OBJECT-TYPE
        SYNTAX       SEQUENCE OF IpeCfgMgmtTrafficControlEntry
        MAX-ACCESS   not-accessible
        STATUS       current
        DESCRIPTION  "This table configures the M-plane traffic."
        ::= { ipeCfgMgmtTrafficGrop 1 }

    ipeCfgMgmtTrafficControlEntry OBJECT-TYPE
        SYNTAX       IpeCfgMgmtTrafficControlEntry
        MAX-ACCESS   not-accessible
        STATUS       current
        DESCRIPTION  ""
        INDEX        { ipeCfgMgmtTrafficControlIndex }
        ::= { ipeCfgMgmtTrafficControlTable 1 }

    IpeCfgMgmtTrafficControlEntry ::= SEQUENCE {
        ipeCfgMgmtTrafficControlIndex      Integer32,
        ipeCfgMgmtTrafficControlNEAddress  IpAddress,
        ipeCfgMgmtTrafficRate              Integer32,
        ipeCfgMgmtTraffcEgressCos          Integer32
    }

    ipeCfgMgmtTrafficControlIndex OBJECT-TYPE
        SYNTAX       Integer32 (1..1)
        MAX-ACCESS   not-accessible
        STATUS       current
        DESCRIPTION  "Indef of this table."
        ::= { ipeCfgMgmtTrafficControlEntry 1 }

    ipeCfgMgmtTrafficControlNEAddress OBJECT-TYPE
        SYNTAX       IpAddress
        MAX-ACCESS   not-accessible
        STATUS       current
        DESCRIPTION  "reserved."
        ::= { ipeCfgMgmtTrafficControlEntry 2 }

    ipeCfgMgmtTrafficRate OBJECT-TYPE
        SYNTAX       Integer32 (0|500..10000)
        UNITS        "kbps"
        MAX-ACCESS   read-write
        STATUS       current
        DESCRIPTION  
            "The maximum bandwidth of M-plane traffic.
            This object limits the rate of ingress traffic and limits the
            rate of egress traffic to Radio Link (i.e. excluding the
            NMS/NE1/Inband traffic).
            
            Value '0' means the rate limit is disabled.
            
            
            range: 0,500~10000[iPASOLINK200/400/1000series/EX/iX], 
                   0,500~ 2000[iPASOLINK VR series]"
        ::= { ipeCfgMgmtTrafficControlEntry 3 }

    ipeCfgMgmtTraffcEgressCos OBJECT-TYPE
        SYNTAX       Integer32 (0..8)
        MAX-ACCESS   read-write
        STATUS       current
        DESCRIPTION  
            "CoS value for M-plane egress traffic to Radio Link.
            When the CPU sends M-plane data to the Radio link, the frame has
            the CoS value which is configured by this object.
            And the agent controls the priority of egress traffic depending
            on this CoS value.
            
            range: 5~7[iPASOLINK200/400/1000series/EX/iX], 
                   0~7,8(highest)[iPASOLINK VR series]"
        ::= { ipeCfgMgmtTrafficControlEntry 4 }

    ipeCfgMgmtIpRouterGroup OBJECT IDENTIFIER
        ::= { ipeConfigurationGroup 31 }

    ipeCfgMgmtIpRouterTable OBJECT-TYPE
        SYNTAX       SEQUENCE OF IpeCfgMgmtIpRouterEntry
        MAX-ACCESS   not-accessible
        STATUS       current
        DESCRIPTION  
            "This table contains configurations for Management plane router
            behaviour."
        ::= { ipeCfgMgmtIpRouterGroup 1 }

    ipeCfgMgmtIpRouterEntry OBJECT-TYPE
        SYNTAX       IpeCfgMgmtIpRouterEntry
        MAX-ACCESS   not-accessible
        STATUS       current
        DESCRIPTION  ""
        INDEX        { ipeCfgMgmtIpRouterIndex }
        ::= { ipeCfgMgmtIpRouterTable 1 }

    IpeCfgMgmtIpRouterEntry ::= SEQUENCE {
        ipeCfgMgmtIpRouterIndex              Integer32,
        ipeCfgMgmtIpRouterNEAddress          IpAddress,
        ipeCfgMgmtIpRouterDiscardFragmented  EnableDisableValue
    }

    ipeCfgMgmtIpRouterIndex OBJECT-TYPE
        SYNTAX       Integer32 (1..1)
        MAX-ACCESS   not-accessible
        STATUS       current
        DESCRIPTION  
            "Index of this table. The instance is created automatically when
            agent boots."
        ::= { ipeCfgMgmtIpRouterEntry 1 }

    ipeCfgMgmtIpRouterNEAddress OBJECT-TYPE
        SYNTAX       IpAddress
        MAX-ACCESS   not-accessible
        STATUS       current
        DESCRIPTION  "reserved."
        ::= { ipeCfgMgmtIpRouterEntry 2 }

    ipeCfgMgmtIpRouterDiscardFragmented OBJECT-TYPE
        SYNTAX       EnableDisableValue
        MAX-ACCESS   read-write
        STATUS       current
        DESCRIPTION  
            "Indicates whether discarding fragmentation packet is enabled."
        ::= { ipeCfgMgmtIpRouterEntry 3 }

    ipeCfgMgmtArpGroup OBJECT IDENTIFIER
        ::= { ipeConfigurationGroup 32 }

    ipeCfgNetToPhysicalTable OBJECT-TYPE
        SYNTAX       SEQUENCE OF IpeCfgNetToPhysicalEntry
        MAX-ACCESS   not-accessible
        STATUS       current
        DESCRIPTION  
            "This table configures IP Address Translation table used for
            mapping from IP addresses to physical addresses.
            
            The status of the entries which were created thru this table is
            reported by ipNetToPhysicalTable."
        ::= { ipeCfgMgmtArpGroup 1 }

    ipeCfgNetToPhysicalEntry OBJECT-TYPE
        SYNTAX       IpeCfgNetToPhysicalEntry
        MAX-ACCESS   not-accessible
        STATUS       current
        DESCRIPTION  ""
        INDEX        {
                         ipeCfgNetToPhysicalNetAddressType,
                         ipeCfgNetToPhysicalNetAddress
                     }
        ::= { ipeCfgNetToPhysicalTable 1 }

    IpeCfgNetToPhysicalEntry ::= SEQUENCE {
        ipeCfgNetToPhysicalNetAddressType  InetAddressType,
        ipeCfgNetToPhysicalNetAddress      InetAddress,
        ipeCfgNetToPhysicalNEAddress       IpAddress,
        ipeCfgNetToPhysicalPhysAddress     PhysAddress,
        ipeCfgNetToPhysicalRowStatus       RowStatus
    }

    ipeCfgNetToPhysicalNetAddressType OBJECT-TYPE
        SYNTAX       InetAddressType
        MAX-ACCESS   not-accessible
        STATUS       current
        DESCRIPTION  "The type of ipeCfgNetToPhysicalNetAddress."
        ::= { ipeCfgNetToPhysicalEntry 1 }

    ipeCfgNetToPhysicalNetAddress OBJECT-TYPE
        SYNTAX       InetAddress
        MAX-ACCESS   not-accessible
        STATUS       current
        DESCRIPTION  
            "The IP Address corresponding to the media-dependent 'physical'
            address.  The address type of this object is specified in
            ipeCfgNetToPhysicalNetAddressType."
        ::= { ipeCfgNetToPhysicalEntry 2 }

    ipeCfgNetToPhysicalNEAddress OBJECT-TYPE
        SYNTAX       IpAddress
        MAX-ACCESS   not-accessible
        STATUS       current
        DESCRIPTION  "reserved"
        ::= { ipeCfgNetToPhysicalEntry 3 }

    ipeCfgNetToPhysicalPhysAddress OBJECT-TYPE
        SYNTAX       PhysAddress
        MAX-ACCESS   read-create
        STATUS       current
        DESCRIPTION  "The media-dependent 'physical' address."
        ::= { ipeCfgNetToPhysicalEntry 4 }

    ipeCfgNetToPhysicalRowStatus OBJECT-TYPE
        SYNTAX       RowStatus
        MAX-ACCESS   read-create
        STATUS       current
        DESCRIPTION  "The status of this conceptual row."
        ::= { ipeCfgNetToPhysicalEntry 5 }

    ipeCfgMgmtInbandGroup OBJECT IDENTIFIER
        ::= { ipeConfigurationGroup 33 }

    ipeCfgMgmtInbandTable OBJECT-TYPE
        SYNTAX       SEQUENCE OF IpeCfgMgmtInbandEntry
        MAX-ACCESS   not-accessible
        STATUS       current
        DESCRIPTION  
            "This table contains management interface mode information."
        ::= { ipeCfgMgmtInbandGroup 1 }

    ipeCfgMgmtInbandEntry OBJECT-TYPE
        SYNTAX       IpeCfgMgmtInbandEntry
        MAX-ACCESS   not-accessible
        STATUS       current
        DESCRIPTION  ""
        INDEX        { ipeCfgMgmtInbandIndex }
        ::= { ipeCfgMgmtInbandTable 1 }

    IpeCfgMgmtInbandEntry ::= SEQUENCE {
        ipeCfgMgmtInbandIndex        Integer32,
        ipeCfgMgmtInbandNEAddress    IpAddress,
        ipeCfgMgmtInbandVlanTagType  INTEGER
    }

    ipeCfgMgmtInbandIndex OBJECT-TYPE
        SYNTAX       Integer32 (1..1)
        MAX-ACCESS   not-accessible
        STATUS       current
        DESCRIPTION  "Index of this table."
        ::= { ipeCfgMgmtInbandEntry 1 }

    ipeCfgMgmtInbandNEAddress OBJECT-TYPE
        SYNTAX       IpAddress
        MAX-ACCESS   not-accessible
        STATUS       current
        DESCRIPTION  "reserved."
        ::= { ipeCfgMgmtInbandEntry 2 }

    ipeCfgMgmtInbandVlanTagType OBJECT-TYPE
        SYNTAX       INTEGER { ctag(2), stag(3) }
        MAX-ACCESS   read-write
        STATUS       current
        DESCRIPTION  "INBAND Management VLAN Tag Type."
        DEFVAL       { ctag }
        ::= { ipeCfgMgmtInbandEntry 3 }

    ipeCfgSysDcnPortTable OBJECT-TYPE
        SYNTAX       SEQUENCE OF IpeCfgSysDcnPortEntry
        MAX-ACCESS   not-accessible
        STATUS       current
        DESCRIPTION  "DCN Port Mode Configuration Table."
        ::= { ipeConfigurationGroup 34 }

    ipeCfgSysDcnPortEntry OBJECT-TYPE
        SYNTAX       IpeCfgSysDcnPortEntry
        MAX-ACCESS   not-accessible
        STATUS       current
        DESCRIPTION  ""
        INDEX        { ipeCfgSysDcnPortIndex }
        ::= { ipeCfgSysDcnPortTable 1 }

    IpeCfgSysDcnPortEntry ::= SEQUENCE {
        ipeCfgSysDcnPortIndex      Integer32,
        ipeCfgSysDcnPortNEAddress  IpAddress,
        ipeCfgSysDcnPortMode       INTEGER
    }

    ipeCfgSysDcnPortIndex OBJECT-TYPE
        SYNTAX       Integer32 (1..1)
        MAX-ACCESS   not-accessible
        STATUS       current
        DESCRIPTION  "Index of this table."
        ::= { ipeCfgSysDcnPortEntry 1 }

    ipeCfgSysDcnPortNEAddress OBJECT-TYPE
        SYNTAX       IpAddress
        MAX-ACCESS   not-accessible
        STATUS       current
        DESCRIPTION  ""
        ::= { ipeCfgSysDcnPortEntry 2 }

    ipeCfgSysDcnPortMode OBJECT-TYPE
        SYNTAX       INTEGER { invalid(0), userport(1), lctport(2), nmsport(3) }
        MAX-ACCESS   read-write
        STATUS       current
        DESCRIPTION  "DCN Port Mode Configuration"
        DEFVAL       { lctPort }
        ::= { ipeCfgSysDcnPortEntry 3 }

    ipeCommunicationsGroup OBJECT IDENTIFIER
        ::= { system5 4 }

    ipeNeighborInfoTable OBJECT-TYPE
        SYNTAX       SEQUENCE OF IpeNeighborInfoEntry
        MAX-ACCESS   not-accessible
        STATUS       current
        DESCRIPTION  "Neighbor NE table."
        ::= { ipeCommunicationsGroup 1 }

    ipeNeighborInfoEntry OBJECT-TYPE
        SYNTAX       IpeNeighborInfoEntry
        MAX-ACCESS   not-accessible
        STATUS       current
        DESCRIPTION  "Neighbor NE entry."
        INDEX        { ipeNeighborInfoIndex }
        ::= { ipeNeighborInfoTable 1 }

    IpeNeighborInfoEntry ::= SEQUENCE {
        ipeNeighborInfoIndex        InterfaceIndex,
        ipeNeighborInfoNEAddress    IpAddress,
        ipeNeighborIpAddress        OCTET STRING,
        ipeNeighborIpv4Ipv6Address  OCTET STRING
    }

    ipeNeighborInfoIndex OBJECT-TYPE
        SYNTAX       InterfaceIndex
        MAX-ACCESS   not-accessible
        STATUS       current
        DESCRIPTION  "Index of table."
        ::= { ipeNeighborInfoEntry 1 }

    ipeNeighborInfoNEAddress OBJECT-TYPE
        SYNTAX       IpAddress
        MAX-ACCESS   not-accessible
        STATUS       current
        DESCRIPTION  ""
        ::= { ipeNeighborInfoEntry 2 }

    ipeNeighborIpAddress OBJECT-TYPE
        SYNTAX       OCTET STRING (SIZE(0..240))
        MAX-ACCESS   read-only
        STATUS       current
        DESCRIPTION  
            "[iPASOLINK200/400/1000series/EX/iX]
            Neighbor NE is displayed as unit of registration every eight
            bytes of Internet Protocol address (4byte) + Node TYPE(4byte).The
            number of maximum registration is 30 (240byte). Attention: ne2
            set the IpAddress only, do not set the Node type.
            
            [iPASOLINK VR series/iPASOLINK EX Advanced]
            The number of maximum registration is 13.
            Type(1byte) and Length(1byte) are common information is 2byte.
            
            Unit of registration of each neighbor as 
            IPv4 Address(4bytes) + Node Type(4bytes) + MAC Address(6bytes) +
            ifindex(4bytes)."
        ::= { ipeNeighborInfoEntry 3 }

    ipeNeighborIpv4Ipv6Address OBJECT-TYPE
        SYNTAX       OCTET STRING (SIZE(0..512))
        MAX-ACCESS   read-only
        STATUS       current
        DESCRIPTION  
            "[EX CPRI]
            The number of maximum registration is 17 (510byte).
            Type(7bit) and Length(9bit) are common information is 2byte.
            
            Unit of registration of each neighbor as IPv6 Address(16byte) +
            IPv4 Address(4byte) + Node Type(4byte) + MAC address(6byte).
            
            [iPASOLINK VR series/iPASOLINK iX/iPASOLINK EX Advanced]
            The number of maximum registration is 15.
            Type(7bit) and Length(9bit) are common information is 2byte.
            
            Unit of registration of each neighbor as IPv6 Address(16bytes) +
            IPv4 Address(4bytes) + Node Type(4bytes) + MAC Address(6bytes) +
            ifindex(4bytes)."
        ::= { ipeNeighborInfoEntry 4 }

-----------------------------------------------
-- End User MIB Object Definitions
-----------------------------------------------

END
