--
-- ASN.1 MIB Definitions
-- Output Date: Fri Mar 05 09:45:17 2021
--

IPE-ETH-RING-MIB DEFINITIONS ::= BEGIN

-----------------------------------------------
-- IMPORTS Definitions
-----------------------------------------------

    IMPORTS
        InterfaceIndex
            FROM IF-MIB
        enterprises, Integer32, IpAddress, NOTIFICATION-TYPE, OBJECT-TYPE
            FROM SNMPv2-SMI
        DisplayString, RowStatus, TEXTUAL-CONVENTION
            FROM SNMPv2-TC;

-----------------------------------------------
-- Textual Convention Definitions
-----------------------------------------------

    IpeAdminStatus ::= TEXTUAL-CONVENTION
        STATUS       current
        DESCRIPTION  ""
        SYNTAX       INTEGER { invalid(0), down(1), up(2) }

    IpeEnableDisableValue ::= TEXTUAL-CONVENTION
        STATUS       current
        DESCRIPTION  ""
        SYNTAX       INTEGER { invalid(0), disabled(1), enabled(2) }

    IpeEtherRingIndex ::= TEXTUAL-CONVENTION
        DISPLAY-HINT "d"
        STATUS       current
        DESCRIPTION  "EtherRing Instance Index."
        SYNTAX       Integer32 (1..16)

    IpeEtherRingIndexOrZero ::= TEXTUAL-CONVENTION
        DISPLAY-HINT "d"
        STATUS       current
        DESCRIPTION  "EtherRing Instance Index with zero value."
        SYNTAX       Integer32 (0..16)

    IpeEtherRingPortId ::= TEXTUAL-CONVENTION
        DISPLAY-HINT "d"
        STATUS       current
        DESCRIPTION  ""
        SYNTAX       Integer32 (1..2)

    IpeEtherRingPortIdOrZero ::= TEXTUAL-CONVENTION
        DISPLAY-HINT "d"
        STATUS       current
        DESCRIPTION  ""
        SYNTAX       Integer32 (0..2)

    IpeEtherRingProtoVersion ::= TEXTUAL-CONVENTION
        STATUS       current
        DESCRIPTION  "Definition of EtherRing Protocol Version."
        SYNTAX       INTEGER { invalid(0), g8032v1(1), g8032v2(2) }

    IpeEtherRingVlanIndex ::= TEXTUAL-CONVENTION
        DISPLAY-HINT "d"
        STATUS       current
        DESCRIPTION  "Definition of VLAN ID. VLAN ID 4095 is reserved."
        SYNTAX       Integer32 (1..4094)

    IpeMepIdOrZero ::= TEXTUAL-CONVENTION
        DISPLAY-HINT "d"
        STATUS       current
        DESCRIPTION  
            "Administrative MEP ID value.
            This value is not same as MEP ID in protocol sense. And value 0
            means no MEP is specified."
        SYNTAX       Integer32 (0..128)

    IpeRingType ::= TEXTUAL-CONVENTION
        STATUS       current
        DESCRIPTION  ""
        SYNTAX       INTEGER { invalid(0), major(1), sub(2) }

    IpeVlanList ::= TEXTUAL-CONVENTION
        STATUS       current
        DESCRIPTION  ""
        SYNTAX       OCTET STRING (SIZE(512..512))

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    alarmStatusGroup OBJECT IDENTIFIER
        ::= { pasoNeoIpe-common 3 }

-----------------------------------------------
-- alarmStatusGroup Definitions
-----------------------------------------------

    asEtherRingGroup OBJECT IDENTIFIER
        ::= { alarmStatusGroup 39 }

    asEtherRingTable OBJECT-TYPE
        SYNTAX       SEQUENCE OF AsEtherRingEntry
        MAX-ACCESS   not-accessible
        STATUS       current
        DESCRIPTION  
            "This table contains Alarm & Status of Ethernet Ring Instance."
        ::= { asEtherRingGroup 1 }

    asEtherRingEntry OBJECT-TYPE
        SYNTAX       AsEtherRingEntry
        MAX-ACCESS   not-accessible
        STATUS       current
        DESCRIPTION  ""
        INDEX        { asEtherRingRingIndex }
        ::= { asEtherRingTable 1 }

    AsEtherRingEntry ::= SEQUENCE {
        asEtherRingRingIndex            IpeEtherRingIndex,
        asEtherRingNEAddress            IpAddress,
        asEtherRingState                INTEGER,
        asEtherRingCause                INTEGER,
        asEtherRingMultiRplOwnerDetect  INTEGER
    }

    asEtherRingRingIndex OBJECT-TYPE
        SYNTAX       IpeEtherRingIndex
        MAX-ACCESS   not-accessible
        STATUS       current
        DESCRIPTION  "Index of this table."
        ::= { asEtherRingEntry 1 }

    asEtherRingNEAddress OBJECT-TYPE
        SYNTAX       IpAddress
        MAX-ACCESS   not-accessible
        STATUS       current
        DESCRIPTION  "reserved."
        ::= { asEtherRingEntry 2 }

    asEtherRingState OBJECT-TYPE
        SYNTAX       INTEGER {
                         invalid(0),
                         disabled(1),
                         idle(2),
                         protection(3),
                         forced(4),
                         manual(5),
                         pending(6)
                     }
        MAX-ACCESS   read-only
        STATUS       current
        DESCRIPTION  
            "The status of Etherring instance.
            The value 'idle' is initial and normal value. And that means
            there is no fault on the Ring Network (i.e. the RPL Port is
            closed). When the RPL port is opened because of the detection of
            Signal Failure on the Network, the value will change to
            'protection'. 'force' and 'manual' shows switch control is
            performed on the Ring Network. When the switch control is cleared
            or the Signal Failure is cleared, the value will show 'pending'."
        ::= { asEtherRingEntry 3 }

    asEtherRingCause OBJECT-TYPE
        SYNTAX       INTEGER {
                         invalid(0),
                         none(1),
                         localSf(2),
                         localNr(3),
                         remoteSf(4),
                         remoteNr(5),
                         localFs(6),
                         localMs(7),
                         remoteFs(8),
                         remoteMs(9)
                     }
        MAX-ACCESS   read-only
        STATUS       current
        DESCRIPTION  
            "The object shows the reason of the asEtherRingStatus change.
             'localSf' : Signal Failure of the local node.
             'localNr' : Normal Request of the local node.
             'remoteSf' : Signal Failure from the other node.
             'remoteNr' : Normal Request from the other node.
             'localFs' : Forced Switch Request of the local node.
             'localMs' : Manual Switch Request of the local node.
             'remoteFs' : Forced Switch Request from the other node.
             'remoteMs' : Manual Switch Request from the other node."
        ::= { asEtherRingEntry 4 }

    asEtherRingMultiRplOwnerDetect OBJECT-TYPE
        SYNTAX       INTEGER { invalid(0), none(1), detected(2) }
        MAX-ACCESS   read-only
        STATUS       current
        DESCRIPTION  
            "when the multiple RPL Owner is detected on the Ring Network, the
            value will change to 'detected'."
        ::= { asEtherRingEntry 5 }

    asEtherRingPortTable OBJECT-TYPE
        SYNTAX       SEQUENCE OF AsEtherRingPortEntry
        MAX-ACCESS   not-accessible
        STATUS       current
        DESCRIPTION  
            "This table contains Alarm & Status of Ethernet Ring Instance."
        ::= { asEtherRingGroup 2 }

    asEtherRingPortEntry OBJECT-TYPE
        SYNTAX       AsEtherRingPortEntry
        MAX-ACCESS   not-accessible
        STATUS       current
        DESCRIPTION  ""
        INDEX        { asEtherRingPortRingIndex, asEtherRingPortId }
        ::= { asEtherRingPortTable 1 }

    AsEtherRingPortEntry ::= SEQUENCE {
        asEtherRingPortRingIndex     IpeEtherRingIndex,
        asEtherRingPortId            IpeEtherRingPortId,
        asEtherRingPortNEAddress     IpAddress,
        asEtherRingPortState         INTEGER,
        asEtherRingPortLoopDetect    INTEGER,
        asEtherRingPortProtoTimeout  INTEGER
    }

    asEtherRingPortRingIndex OBJECT-TYPE
        SYNTAX       IpeEtherRingIndex
        MAX-ACCESS   not-accessible
        STATUS       current
        DESCRIPTION  "Ethernet Ring Instance number."
        ::= { asEtherRingPortEntry 1 }

    asEtherRingPortId OBJECT-TYPE
        SYNTAX       IpeEtherRingPortId
        MAX-ACCESS   not-accessible
        STATUS       current
        DESCRIPTION  
            "Index of this table. This object represents the Ring port id of
            the ring instance."
        ::= { asEtherRingPortEntry 2 }

    asEtherRingPortNEAddress OBJECT-TYPE
        SYNTAX       IpAddress
        MAX-ACCESS   not-accessible
        STATUS       current
        DESCRIPTION  "reserved."
        ::= { asEtherRingPortEntry 3 }

    asEtherRingPortState OBJECT-TYPE
        SYNTAX       INTEGER {
                         invalid(0),
                         disabled(1),
                         initBlocking(2),
                         rplBlocking(3),
                         forwarding(4),
                         signalFail(5),
                         recovery(6),
                         waitToRestore(7),
                         forcedSwitch(8),
                         manualSwitch(9),
                         waitToBlock(10)
                     }
        MAX-ACCESS   read-only
        STATUS       current
        DESCRIPTION  
            "Port Status.
            'initBlocking' is the initial value. At this point the no R-APS
            frame is received. When the port is configured as RPL port and
            the port is closed, the value will show 'rplBlocking'. The port
            forwards the frames, the value will show 'forwarding'.
            If the signal failure is detected on the port and the port is
            closed, the object will return the value 'signalFail'. And then
            the condition of Signal Failure is cleared but the port is still
            closed, the object will return the value 'recovery'.
            'waitToRestore' shows the RPL port is still closed till expiring
            the wait-to-restore timer.
            'forcedSwitch' and 'manualSwitch' represents the port is
            controlled by the maintenance control. 'waitToBlock' is waiting
            the RPL Port open after clearing maintenance control."
        ::= { asEtherRingPortEntry 4 }

    asEtherRingPortLoopDetect OBJECT-TYPE
        SYNTAX       INTEGER { invalid(0), none(1), detected(2) }
        MAX-ACCESS   read-only
        STATUS       current
        DESCRIPTION  
            "The loop detection status.
            The object will show the value 'detected', when the Loop
            connection is detected."
        ::= { asEtherRingPortEntry 5 }

    asEtherRingPortProtoTimeout OBJECT-TYPE
        SYNTAX       INTEGER { invalid(0), none(1), detected(2) }
        MAX-ACCESS   read-only
        STATUS       current
        DESCRIPTION  
            "The status of Protocol Timeout.
            If the R-APS frame is not received in a specified time, the
            object will show the value 'detected'."
        ::= { asEtherRingPortEntry 6 }

-----------------------------------------------
-- End User MIB Object Definitions
-----------------------------------------------

END
