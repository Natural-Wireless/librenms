--
-- ASN.1 MIB Definitions
-- Output Date: Fri Mar 05 09:45:24 2021
--

IPE-MSTP-MIB DEFINITIONS ::= BEGIN

-----------------------------------------------
-- IMPORTS Definitions
-----------------------------------------------

    IMPORTS
        BridgeId
            FROM BRIDGE-MIB
        InterfaceIndex
            FROM IF-MIB
        Counter32, enterprises, Integer32, IpAddress, NOTIFICATION-TYPE,
        OBJECT-TYPE
            FROM SNMPv2-SMI
        DisplayString, RowStatus, TEXTUAL-CONVENTION
            FROM SNMPv2-TC;

-----------------------------------------------
-- Textual Convention Definitions
-----------------------------------------------

    EnableDisableValue ::= TEXTUAL-CONVENTION
        STATUS       current
        DESCRIPTION  "Enable/Disable Type"
        SYNTAX       INTEGER { invalid(0), disable(1), enable(2) }

    IpeBridgePriority ::= TEXTUAL-CONVENTION
        DISPLAY-HINT "d"
        STATUS       current
        DESCRIPTION  ""
        SYNTAX       Integer32 (0..61440)

    IpePortPathCost ::= TEXTUAL-CONVENTION
        DISPLAY-HINT "d"
        STATUS       current
        DESCRIPTION  ""
        SYNTAX       Integer32 (0..200000000)

    IpePortPriority ::= TEXTUAL-CONVENTION
        DISPLAY-HINT "d"
        STATUS       current
        DESCRIPTION  ""
        SYNTAX       Integer32 (0..240)

    IpePortRole ::= TEXTUAL-CONVENTION
        STATUS       current
        DESCRIPTION  ""
        SYNTAX       INTEGER {
                         invalid(0),
                         disabled(1),
                         alternate(2),
                         backup(3),
                         root(4),
                         designated(5)
                     }

    IpePortState ::= TEXTUAL-CONVENTION
        STATUS       current
        DESCRIPTION  ""
        SYNTAX       INTEGER {
                         invalid(0),
                         disabled(1),
                         blocking(2),
                         listening(3),
                         learning(4),
                         forwarding(5),
                         restricted(8),
                         guarded(9)
                     }

    IpeVlanList ::= TEXTUAL-CONVENTION
        STATUS       current
        DESCRIPTION  ""
        SYNTAX       OCTET STRING (SIZE(512..512))

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    alarmStatusGroup OBJECT IDENTIFIER
        ::= { pasoNeoIpe-common 3 }

-----------------------------------------------
-- alarmStatusGroup Definitions
-----------------------------------------------

    asMstpGroup OBJECT IDENTIFIER
        ::= { alarmStatusGroup 44 }

    asMstpBridgeCistTable OBJECT-TYPE
        SYNTAX       SEQUENCE OF AsMstpBridgeCistEntry
        MAX-ACCESS   not-accessible
        STATUS       current
        DESCRIPTION  
            "The Common and Internal Spanning Tree (CIST) Alarm/Status
            table."
        ::= { asMstpGroup 1 }

    asMstpBridgeCistEntry OBJECT-TYPE
        SYNTAX       AsMstpBridgeCistEntry
        MAX-ACCESS   not-accessible
        STATUS       current
        DESCRIPTION  "A CIST Table Entry."
        INDEX        { asMstpBridgeCistIndex }
        ::= { asMstpBridgeCistTable 1 }

    AsMstpBridgeCistEntry ::= SEQUENCE {
        asMstpBridgeCistIndex         Integer32,
        asMstpBridgeCistNEAddress     IpAddress,
        asMstpBridgeCistRegionalRoot  BridgeId,
        asMstpBridgeCistTopChanges    Counter32,
        asMstpBridgeCistRoot          BridgeId
    }

    asMstpBridgeCistIndex OBJECT-TYPE
        SYNTAX       Integer32 (1..1)
        MAX-ACCESS   not-accessible
        STATUS       current
        DESCRIPTION  "Index of this table."
        ::= { asMstpBridgeCistEntry 1 }

    asMstpBridgeCistNEAddress OBJECT-TYPE
        SYNTAX       IpAddress
        MAX-ACCESS   not-accessible
        STATUS       obsolete
        DESCRIPTION  "reserved."
        ::= { asMstpBridgeCistEntry 2 }

    asMstpBridgeCistRegionalRoot OBJECT-TYPE
        SYNTAX       BridgeId
        MAX-ACCESS   read-only
        STATUS       current
        DESCRIPTION  
            "In an MSTP Bridge, the CIST Regional Root Identifier parameter,
            i.e. the Bridge Identifier of the current CIST Regional Root."
        ::= { asMstpBridgeCistEntry 3 }

    asMstpBridgeCistTopChanges OBJECT-TYPE
        SYNTAX       Counter32
        MAX-ACCESS   read-only
        STATUS       current
        DESCRIPTION  
            "MSTP Topology Changed Status. The total number of topology
            chagnes detected by this bridge since the equipment was last
            initialized."
        ::= { asMstpBridgeCistEntry 4 }

    asMstpBridgeCistRoot OBJECT-TYPE
        SYNTAX       BridgeId
        MAX-ACCESS   read-only
        STATUS       current
        DESCRIPTION  ""
        ::= { asMstpBridgeCistEntry 5 }

    asMstpBridgeMstTable OBJECT-TYPE
        SYNTAX       SEQUENCE OF AsMstpBridgeMstEntry
        MAX-ACCESS   not-accessible
        STATUS       current
        DESCRIPTION  
            "In an MSTP Bridge, the MSTP Table. Each row in the Table
            represents information regarding a Bridge's Bridge Protocol
            Entity for the specified Spanning Tree instance.
            
            Entries in this table is retained across reinitializations of the
            management system."
        ::= { asMstpGroup 2 }

    asMstpBridgeMstEntry OBJECT-TYPE
        SYNTAX       AsMstpBridgeMstEntry
        MAX-ACCESS   not-accessible
        STATUS       current
        DESCRIPTION  "A MSTP Table entry."
        INDEX        { asMstpBridgeMstIndex }
        ::= { asMstpBridgeMstTable 1 }

    AsMstpBridgeMstEntry ::= SEQUENCE {
        asMstpBridgeMstIndex         Integer32,
        asMstpBridgeMstNEAddress     IpAddress,
        asMstpBridgeMstRegionalRoot  BridgeId,
        asMstpBridgeMstTopChanges    Counter32
    }

    asMstpBridgeMstIndex OBJECT-TYPE
        SYNTAX       Integer32 (1..4)
        MAX-ACCESS   not-accessible
        STATUS       current
        DESCRIPTION  
            "In an MSTP Bridge, this parameter is the MSTID, i.e. the
            identifier of a Spanning Tree (or MST) Instance."
        ::= { asMstpBridgeMstEntry 1 }

    asMstpBridgeMstNEAddress OBJECT-TYPE
        SYNTAX       IpAddress
        MAX-ACCESS   not-accessible
        STATUS       obsolete
        DESCRIPTION  "reserved."
        ::= { asMstpBridgeMstEntry 2 }

    asMstpBridgeMstRegionalRoot OBJECT-TYPE
        SYNTAX       BridgeId
        MAX-ACCESS   read-only
        STATUS       current
        DESCRIPTION  
            "In an MSTP Bridge, the Designated Root parameter value, i.e. the
            Bridge Identifier of the Root Bridge for the MSTI."
        ::= { asMstpBridgeMstEntry 3 }

    asMstpBridgeMstTopChanges OBJECT-TYPE
        SYNTAX       Counter32
        MAX-ACCESS   read-only
        STATUS       current
        DESCRIPTION  
            "In an MSTP Bridge, count of the times tcWhile has been
            non-zero for any Port for the MSTI since the Bridge was powered
            on or initialized."
        ::= { asMstpBridgeMstEntry 4 }

    asMstpPortCistTable OBJECT-TYPE
        SYNTAX       SEQUENCE OF AsMstpPortCistEntry
        MAX-ACCESS   not-accessible
        STATUS       current
        DESCRIPTION  
            "The CIST Port Table. Each row in the Table represents
            information regarding a specific Port within the Bridge's Bridge
            Protocol Entity, for the CIST."
        ::= { asMstpGroup 3 }

    asMstpPortCistEntry OBJECT-TYPE
        SYNTAX       AsMstpPortCistEntry
        MAX-ACCESS   not-accessible
        STATUS       current
        DESCRIPTION  "A CIST Port Table entry."
        INDEX        { asMstpPortCistIfIndex }
        ::= { asMstpPortCistTable 1 }

    AsMstpPortCistEntry ::= SEQUENCE {
        asMstpPortCistIfIndex             InterfaceIndex,
        asMstpPortCistNEAddress           IpAddress,
        asMstpPortCistRole                IpePortRole,
        asMstpPortCistState               IpePortState,
        asMstpPortCistRegionalRoot        BridgeId,
        asMstpPortCistProtoVersion        INTEGER,
        asMstpPortCistPathCost            Integer32,
        asMstpPortCistInvalidBpdu         INTEGER,
        asMstpPortCistDesignatedPathCost  Integer32,
        asMstpPortCistDesignatedBridge    BridgeId,
        asMstpPortCistDesignatedPort      OCTET STRING,
        asMstpPortCistForwardTransitions  Counter32,
        asMstpPortCistOperEdgePort        INTEGER
    }

    asMstpPortCistIfIndex OBJECT-TYPE
        SYNTAX       InterfaceIndex
        MAX-ACCESS   not-accessible
        STATUS       current
        DESCRIPTION  "Index of this table."
        ::= { asMstpPortCistEntry 1 }

    asMstpPortCistNEAddress OBJECT-TYPE
        SYNTAX       IpAddress
        MAX-ACCESS   not-accessible
        STATUS       obsolete
        DESCRIPTION  "reserved."
        ::= { asMstpPortCistEntry 2 }

    asMstpPortCistRole OBJECT-TYPE
        SYNTAX       IpePortRole
        MAX-ACCESS   read-only
        STATUS       current
        DESCRIPTION  
            "The current Port Role for the Port (i.e., Root, Alternate,
            Designated, or Backup), for the CIST."
        ::= { asMstpPortCistEntry 3 }

    asMstpPortCistState OBJECT-TYPE
        SYNTAX       IpePortState
        MAX-ACCESS   read-only
        STATUS       current
        DESCRIPTION  
            "In an MSTP Bridge, the current state of the Port (i.e.,
            Disabled, Listening, Learning, Forwarding, or Blocking), for the
            MSTI."
        ::= { asMstpPortCistEntry 4 }

    asMstpPortCistRegionalRoot OBJECT-TYPE
        SYNTAX       BridgeId
        MAX-ACCESS   read-only
        STATUS       current
        DESCRIPTION  
            "In an MSTP Bridge, the CIST Regional Root Identifier, i.e. the
            Bridge Identifier of the current CIST Regional Root, for the
            CIST."
        ::= { asMstpPortCistEntry 5 }

    asMstpPortCistProtoVersion OBJECT-TYPE
        SYNTAX       INTEGER { invalid(0), stp(1), rstp(2), mstp(3) }
        MAX-ACCESS   read-only
        STATUS       current
        DESCRIPTION  
            "In an MSTP Bridge, the current version of xSTP Protocol for the
            Port."
        ::= { asMstpPortCistEntry 6 }

    asMstpPortCistPathCost OBJECT-TYPE
        SYNTAX       Integer32
        MAX-ACCESS   read-only
        STATUS       current
        DESCRIPTION  
            "In an MSTP Bridge, the CIST Path Cost parameter, i.e. the
            CISTpath cost from the transmitting Bridge to the CIST Regional
            Root. The sum (about 20 possible out of the given range) of
            multiple port path costs. Also, if the 'transmitting Bridge' is
            the 'CIST Regional Root', then this value could be zero."
        ::= { asMstpPortCistEntry 7 }

    asMstpPortCistInvalidBpdu OBJECT-TYPE
        SYNTAX       INTEGER { invalid(0) }
        MAX-ACCESS   read-only
        STATUS       current
        DESCRIPTION  ""
        ::= { asMstpPortCistEntry 8 }

    asMstpPortCistDesignatedPathCost OBJECT-TYPE
        SYNTAX       Integer32
        MAX-ACCESS   read-only
        STATUS       current
        DESCRIPTION  
            "In an MSTP Bridge, the CIST Path Cost parameter, i.e. the CIST
            path cost from the transmitting Bridge to the CIST Regional Root.
            The sum (about 20 possible out of the given range) of multiple
            port path costs. Also, if the 'transmitting Bridge' is the 'CIST
            Regional Root', then this value could be zero."
        ::= { asMstpPortCistEntry 9 }

    asMstpPortCistDesignatedBridge OBJECT-TYPE
        SYNTAX       BridgeId
        MAX-ACCESS   read-only
        STATUS       current
        DESCRIPTION  
            "In an MSTP Bridge, the Designated Root parameter value, i.e. the
            Bridge Identifier of the Root Bridge for the MSTI."
        ::= { asMstpPortCistEntry 10 }

    asMstpPortCistDesignatedPort OBJECT-TYPE
        SYNTAX       OCTET STRING
        MAX-ACCESS   read-only
        STATUS       current
        DESCRIPTION  
            "The CIST Regional Root Identifier component of the Port's port
            priority vector for the CIST."
        ::= { asMstpPortCistEntry 11 }

    asMstpPortCistForwardTransitions OBJECT-TYPE
        SYNTAX       Counter32
        MAX-ACCESS   read-only
        STATUS       current
        DESCRIPTION  
            "The number of times this port has transitioned from the Learning
            state to the Forwarding state."
        ::= { asMstpPortCistEntry 12 }

    asMstpPortCistOperEdgePort OBJECT-TYPE
        SYNTAX       INTEGER { alarmOff(0), alarmOn(1) }
        MAX-ACCESS   read-only
        STATUS       current
        DESCRIPTION  
            "The operational value of the Edge Port parameter.
            If the port whose 'provMstpPortCistEdgePort' is 'enable' receives
            the BPDU, the object will be changed to alarmOn.
            
            When the 'provMstpPortCistEdgePort' is 'disable', the object
            always shows 'alarmOff'."
        ::= { asMstpPortCistEntry 13 }

    asMstpPortMstTable OBJECT-TYPE
        SYNTAX       SEQUENCE OF AsMstpPortMstEntry
        MAX-ACCESS   not-accessible
        STATUS       current
        DESCRIPTION  
            "The MSTP Port Table. Each row in the Table represents
            information
            regarding a specific Port within the Bridge's Bridge Protocol
            Entity, for a given MSTI."
        ::= { asMstpGroup 4 }

    asMstpPortMstEntry OBJECT-TYPE
        SYNTAX       AsMstpPortMstEntry
        MAX-ACCESS   not-accessible
        STATUS       current
        DESCRIPTION  "A MSTP Port Table entry."
        INDEX        { asMstpPortMstIfIndex, asMstpPortMstIndex }
        ::= { asMstpPortMstTable 1 }

    AsMstpPortMstEntry ::= SEQUENCE {
        asMstpPortMstIfIndex             InterfaceIndex,
        asMstpPortMstIndex               Integer32,
        asMstpPortMstNEAddress           IpAddress,
        asMstpPortMstRole                IpePortRole,
        asMstpPortMstState               IpePortState,
        asMstpPortMstRegionalRoot        BridgeId,
        asMstpPortMstPathCost            Integer32,
        asMstpPortMstDesignatedPathCost  Integer32,
        asMstpPortMstDesignatedBridge    BridgeId,
        asMstpPortMstDesignatedPort      OCTET STRING
    }

    asMstpPortMstIfIndex OBJECT-TYPE
        SYNTAX       InterfaceIndex
        MAX-ACCESS   not-accessible
        STATUS       current
        DESCRIPTION  
            "Index of this table. The object represents the interface."
        ::= { asMstpPortMstEntry 1 }

    asMstpPortMstIndex OBJECT-TYPE
        SYNTAX       Integer32 (1..4)
        MAX-ACCESS   not-accessible
        STATUS       current
        DESCRIPTION  
            "In an MSTP Bridge, this parameter is the MSTID, i.e. the
            identifier of a Spanning Tree (or MST) Instance."
        ::= { asMstpPortMstEntry 2 }

    asMstpPortMstNEAddress OBJECT-TYPE
        SYNTAX       IpAddress
        MAX-ACCESS   not-accessible
        STATUS       obsolete
        DESCRIPTION  "reserved."
        ::= { asMstpPortMstEntry 3 }

    asMstpPortMstRole OBJECT-TYPE
        SYNTAX       IpePortRole
        MAX-ACCESS   read-only
        STATUS       current
        DESCRIPTION  
            "In an MSTP Bridge, the current Port Role for the Port (i.e.,
            Root, Alternate, Designated, or Backup), for the MSTI."
        ::= { asMstpPortMstEntry 4 }

    asMstpPortMstState OBJECT-TYPE
        SYNTAX       IpePortState
        MAX-ACCESS   read-only
        STATUS       current
        DESCRIPTION  
            "In an MSTP Bridge, the current state of the Port (i.e.,
            Disabled, Listening, Learning, Forwarding, or Blocking), for the
            MSTI."
        ::= { asMstpPortMstEntry 5 }

    asMstpPortMstRegionalRoot OBJECT-TYPE
        SYNTAX       BridgeId
        MAX-ACCESS   read-only
        STATUS       current
        DESCRIPTION  
            "In an MSTP Bridge, the Regional Root Identifier component of the
            Port's MSTI port priority vector for the MSTI."
        ::= { asMstpPortMstEntry 6 }

    asMstpPortMstPathCost OBJECT-TYPE
        SYNTAX       Integer32
        MAX-ACCESS   read-only
        STATUS       current
        DESCRIPTION  
            "In an MSTP Bridge, the Port's Port Path Cost parameter value for
            the MSTI."
        ::= { asMstpPortMstEntry 7 }

    asMstpPortMstDesignatedPathCost OBJECT-TYPE
        SYNTAX       Integer32
        MAX-ACCESS   read-only
        STATUS       current
        DESCRIPTION  
            "In an MSTP Bridge, the Internal Root Path Cost component of the
            Port's MSTI port priority vector for the MSTI."
        ::= { asMstpPortMstEntry 8 }

    asMstpPortMstDesignatedBridge OBJECT-TYPE
        SYNTAX       BridgeId
        MAX-ACCESS   read-only
        STATUS       current
        DESCRIPTION  
            "In an MSTP Bridge, the Designated Bridge Identifier component of
            the Port's MSTI port priority vector for the MSTI."
        ::= { asMstpPortMstEntry 9 }

    asMstpPortMstDesignatedPort OBJECT-TYPE
        SYNTAX       OCTET STRING
        MAX-ACCESS   read-only
        STATUS       current
        DESCRIPTION  
            "In an MSTP Bridge, the Designated Port Identifier component of
            the Port's MSTI port priority vector for the MSTI."
        ::= { asMstpPortMstEntry 10 }

-----------------------------------------------
-- End User MIB Object Definitions
-----------------------------------------------

END
