--
-- ASN.1 MIB Definitions
-- Output Date: Fri Mar 05 09:45:21 2021
--

IPE-LAG-MIB DEFINITIONS ::= BEGIN

-----------------------------------------------
-- IMPORTS Definitions
-----------------------------------------------

    IMPORTS
        InterfaceIndex, InterfaceIndexOrZero
            FROM IF-MIB
        Counter32, enterprises, Integer32, IpAddress, NOTIFICATION-TYPE,
        OBJECT-TYPE
            FROM SNMPv2-SMI
        DisplayString, RowStatus, TEXTUAL-CONVENTION
            FROM SNMPv2-TC;

-----------------------------------------------
-- Textual Convention Definitions
-----------------------------------------------

    IpeEnableDisableValue ::= TEXTUAL-CONVENTION
        STATUS       current
        DESCRIPTION  ""
        SYNTAX       INTEGER { invalid(0), disabled(1), enabled(2) }

    IpeMepIdOrZero ::= TEXTUAL-CONVENTION
        DISPLAY-HINT "d"
        STATUS       current
        DESCRIPTION  
            "Administrative MEP ID value.
            This value is not same as MEP ID in protocol sense. And value 0
            means no MEP is specified."
        SYNTAX       Integer32 (0..128)

    IpeVlanIndexOrZero ::= TEXTUAL-CONVENTION
        DISPLAY-HINT "d"
        STATUS       current
        DESCRIPTION  
            "VLAN ID.
            Value '4095' is reserved, and cannot set to the system.
            Value '0' is special value, and the definition depends on the
            object which uses this TEXTUAL-CONVENTION."
        SYNTAX       Integer32 (0..4094)

    SeverityValue ::= TEXTUAL-CONVENTION
        STATUS       current
        DESCRIPTION  "Severity (CCITT Rec. X.733)"
        SYNTAX       INTEGER {
                         cleared(1),
                         indetermine(2),
                         critical(3),
                         major(4),
                         minor(5),
                         warning(6),
                         notReport(7)
                     }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    alarmStatusGroup OBJECT IDENTIFIER
        ::= { pasoNeoIpe-common 3 }

-----------------------------------------------
-- alarmStatusGroup Definitions
-----------------------------------------------

    asLinkAggrGroup OBJECT IDENTIFIER
        ::= { alarmStatusGroup 38 }

    asLinkAggrGroupTable OBJECT-TYPE
        SYNTAX       SEQUENCE OF AsLinkAggrGroupEntry
        MAX-ACCESS   not-accessible
        STATUS       current
        DESCRIPTION  
            "Alarm/Status for Link Aggregation Group. This table is created
            automatically when the Link Aggregation Group is defined."
        ::= { asLinkAggrGroup 1 }

    asLinkAggrGroupEntry OBJECT-TYPE
        SYNTAX       AsLinkAggrGroupEntry
        MAX-ACCESS   not-accessible
        STATUS       current
        DESCRIPTION  ""
        INDEX        { asLinkAggrGroupIfIndex }
        ::= { asLinkAggrGroupTable 1 }

    AsLinkAggrGroupEntry ::= SEQUENCE {
        asLinkAggrGroupIfIndex     InterfaceIndex,
        asLinkAggrGroupNEAddress   IpAddress,
        asLinkAggrGroupLinkStatus  SeverityValue,
        asLinkAggrGroupLLFStatus   INTEGER,
        asLinkAggrGroupOperStatus  INTEGER
    }

    asLinkAggrGroupIfIndex OBJECT-TYPE
        SYNTAX       InterfaceIndex
        MAX-ACCESS   not-accessible
        STATUS       current
        DESCRIPTION  "Index of this table."
        ::= { asLinkAggrGroupEntry 1 }

    asLinkAggrGroupNEAddress OBJECT-TYPE
        SYNTAX       IpAddress
        MAX-ACCESS   not-accessible
        STATUS       current
        DESCRIPTION  "reserved"
        ::= { asLinkAggrGroupEntry 2 }

    asLinkAggrGroupLinkStatus OBJECT-TYPE
        SYNTAX       SeverityValue
        MAX-ACCESS   read-only
        STATUS       current
        DESCRIPTION  
            "Link Status for Link Aggregation Group. The all member ports
            become link down, this state becomes alarm state.
            But the lower layer is in alarm state, the link status becomes
            'normal' state because of alarm mask function."
        ::= { asLinkAggrGroupEntry 3 }

    asLinkAggrGroupLLFStatus OBJECT-TYPE
        SYNTAX       INTEGER { invalid(0), normal(1), force(2) }
        MAX-ACCESS   read-only
        STATUS       current
        DESCRIPTION  
            "The status for link loss forwarding. 'force' means the interface
            is shutting down by the link loss forwarding."
        ::= { asLinkAggrGroupEntry 4 }

    asLinkAggrGroupOperStatus OBJECT-TYPE
        SYNTAX       INTEGER { invalid(0), linkDown(1), linkUp(2) }
        MAX-ACCESS   read-only
        STATUS       current
        DESCRIPTION  
            "Link Status for Link Aggregation Group. This object keeps
            linkDown state, when the lower layer is in alarm state."
        ::= { asLinkAggrGroupEntry 5 }

    asLinkAggrPortTable OBJECT-TYPE
        SYNTAX       SEQUENCE OF AsLinkAggrPortEntry
        MAX-ACCESS   not-accessible
        STATUS       current
        DESCRIPTION  
            "The Link Aggregation Member Port Status. This table is created
            automatically when a link aggregation group is defined.
            This table is created per each member port per link aggregation
            group."
        ::= { asLinkAggrGroup 2 }

    asLinkAggrPortEntry OBJECT-TYPE
        SYNTAX       AsLinkAggrPortEntry
        MAX-ACCESS   not-accessible
        STATUS       current
        DESCRIPTION  ""
        INDEX        { asLinkAggrPortGroupIfIndex, asLinkAggrPortIfIndex }
        ::= { asLinkAggrPortTable 1 }

    AsLinkAggrPortEntry ::= SEQUENCE {
        asLinkAggrPortGroupIfIndex       InterfaceIndex,
        asLinkAggrPortIfIndex            InterfaceIndex,
        asLinkAggrPortNEAddress          IpAddress,
        asLinkAggrPortStatus             INTEGER,
        asLinkAggrPortActorLacpStatus    BITS,
        asLinkAggrPortPartnerLacpStatus  BITS,
        asLinkAggrPortLoopDetect         INTEGER
    }

    asLinkAggrPortGroupIfIndex OBJECT-TYPE
        SYNTAX       InterfaceIndex
        MAX-ACCESS   not-accessible
        STATUS       current
        DESCRIPTION  "link aggregation group index of this table."
        ::= { asLinkAggrPortEntry 1 }

    asLinkAggrPortIfIndex OBJECT-TYPE
        SYNTAX       InterfaceIndex
        MAX-ACCESS   not-accessible
        STATUS       current
        DESCRIPTION  "member port index of this table."
        ::= { asLinkAggrPortEntry 2 }

    asLinkAggrPortNEAddress OBJECT-TYPE
        SYNTAX       IpAddress
        MAX-ACCESS   not-accessible
        STATUS       current
        DESCRIPTION  "reserved"
        ::= { asLinkAggrPortEntry 3 }

    asLinkAggrPortStatus OBJECT-TYPE
        SYNTAX       INTEGER { invalid(0), active(1), standby(2) }
        MAX-ACCESS   read-only
        STATUS       current
        DESCRIPTION  
            "The port role of the member port.
            'active' means the port forwards/receives the packets on the
            interface."
        ::= { asLinkAggrPortEntry 4 }

    asLinkAggrPortActorLacpStatus OBJECT-TYPE
        SYNTAX       BITS {
                         lacpActivity(0),
                         lacpTimeout(1),
                         aggregation(2),
                         synchronization(3),
                         collecting(4),
                         distributing(5),
                         defaulted(6),
                         expired(7)
                     }
        MAX-ACCESS   read-only
        STATUS       current
        DESCRIPTION  
            "A string of 8 bits, corresponding to the current operational
            values of Actor_State as transmitted by the Actor in LACPDUs."
        ::= { asLinkAggrPortEntry 5 }

    asLinkAggrPortPartnerLacpStatus OBJECT-TYPE
        SYNTAX       BITS {
                         lacpActivity(0),
                         lacpTimeout(1),
                         aggregation(2),
                         synchronization(3),
                         collecting(4),
                         distributing(5),
                         defaulted(6),
                         expired(7)
                     }
        MAX-ACCESS   read-only
        STATUS       current
        DESCRIPTION  
            "A string of 8 bits, corresponding to the current values of
            Actor_State in the most recently received LACPDU transmitted by
            the protocol Partner."
        ::= { asLinkAggrPortEntry 6 }

    asLinkAggrPortLoopDetect OBJECT-TYPE
        SYNTAX       INTEGER { invalid(0), none(1), detected(2) }
        MAX-ACCESS   read-only
        STATUS       current
        DESCRIPTION  
            "LACP Control frames loop detect status for that port. This
            status will be cleared when the condition is not detected for a
            fixed time."
        ::= { asLinkAggrPortEntry 7 }

    asLinkAggrPortStatsTable OBJECT-TYPE
        SYNTAX       SEQUENCE OF AsLinkAggrPortStatsEntry
        MAX-ACCESS   not-accessible
        STATUS       current
        DESCRIPTION  "Link Aggregation Statistics."
        ::= { asLinkAggrGroup 3 }

    asLinkAggrPortStatsEntry OBJECT-TYPE
        SYNTAX       AsLinkAggrPortStatsEntry
        MAX-ACCESS   not-accessible
        STATUS       current
        DESCRIPTION  ""
        INDEX        { asLinkAggrPortStatsIfIndex }
        ::= { asLinkAggrPortStatsTable 1 }

    AsLinkAggrPortStatsEntry ::= SEQUENCE {
        asLinkAggrPortStatsIfIndex           InterfaceIndex,
        asLinkAggrPortStatsNEAddress         IpAddress,
        asLinkAggrPortStatsLACPDUsRx         Counter32,
        asLinkAggrPortStatsLACPDUsTx         Counter32,
        asLinkAggrPortStatsMarkerPDUsRx      Counter32,
        asLinkAggrPortStatsMarkerRespPDUsRx  Counter32,
        asLinkAggrPortStatsMarkerPDUsTx      Counter32,
        asLinkAggrPortStatsMarkerRespPDUsTx  Counter32
    }

    asLinkAggrPortStatsIfIndex OBJECT-TYPE
        SYNTAX       InterfaceIndex
        MAX-ACCESS   not-accessible
        STATUS       current
        DESCRIPTION  
            "Index of this table. This table is created per each member
            port."
        ::= { asLinkAggrPortStatsEntry 1 }

    asLinkAggrPortStatsNEAddress OBJECT-TYPE
        SYNTAX       IpAddress
        MAX-ACCESS   not-accessible
        STATUS       current
        DESCRIPTION  "reserved"
        ::= { asLinkAggrPortStatsEntry 2 }

    asLinkAggrPortStatsLACPDUsRx OBJECT-TYPE
        SYNTAX       Counter32
        MAX-ACCESS   read-only
        STATUS       current
        DESCRIPTION  
            "The number of valid LACPDUs received on this Aggregation Port."
        ::= { asLinkAggrPortStatsEntry 3 }

    asLinkAggrPortStatsLACPDUsTx OBJECT-TYPE
        SYNTAX       Counter32
        MAX-ACCESS   read-only
        STATUS       current
        DESCRIPTION  
            "The number of LACPDUs transmitted on this
            Aggregation Port."
        ::= { asLinkAggrPortStatsEntry 4 }

    asLinkAggrPortStatsMarkerPDUsRx OBJECT-TYPE
        SYNTAX       Counter32
        MAX-ACCESS   read-only
        STATUS       current
        DESCRIPTION  
            "The number of valid Marker PDUs received on this Aggregation
            Port."
        ::= { asLinkAggrPortStatsEntry 5 }

    asLinkAggrPortStatsMarkerRespPDUsRx OBJECT-TYPE
        SYNTAX       Counter32
        MAX-ACCESS   read-only
        STATUS       current
        DESCRIPTION  
            "The number of valid Marker Response PDUs received on this
            Aggregation Port."
        ::= { asLinkAggrPortStatsEntry 6 }

    asLinkAggrPortStatsMarkerPDUsTx OBJECT-TYPE
        SYNTAX       Counter32
        MAX-ACCESS   read-only
        STATUS       current
        DESCRIPTION  
            "The number of Marker PDUs transmitted on this Aggregation Port."
        ::= { asLinkAggrPortStatsEntry 7 }

    asLinkAggrPortStatsMarkerRespPDUsTx OBJECT-TYPE
        SYNTAX       Counter32
        MAX-ACCESS   read-only
        STATUS       current
        DESCRIPTION  
            "The number of Marker Response PDUs transmitted on this
            Aggregation Port."
        ::= { asLinkAggrPortStatsEntry 8 }

    asLinkAggrMtaTable OBJECT-TYPE
        SYNTAX       SEQUENCE OF AsLinkAggrMtaEntry
        MAX-ACCESS   not-accessible
        STATUS       current
        DESCRIPTION  ""
        ::= { asLinkAggrGroup 4 }

    asLinkAggrMtaEntry OBJECT-TYPE
        SYNTAX       AsLinkAggrMtaEntry
        MAX-ACCESS   not-accessible
        STATUS       current
        DESCRIPTION  ""
        INDEX        { asLinkAggrMtaIfIndex }
        ::= { asLinkAggrMtaTable 1 }

    AsLinkAggrMtaEntry ::= SEQUENCE {
        asLinkAggrMtaIfIndex              InterfaceIndex,
        asLinkAggrMtaNEAddress            IpAddress,
        asLinkAggrMtaModeMismatch         SeverityValue,
        asLinkAggrMtaVersion              Integer32,
        asLinkAggrMtaEncapStatus          INTEGER,
        asLinkAggrMtaTCModeMismatch       SeverityValue,
        asLinkAggrMtaTCCalibrationStatus  INTEGER
    }

    asLinkAggrMtaIfIndex OBJECT-TYPE
        SYNTAX       InterfaceIndex
        MAX-ACCESS   not-accessible
        STATUS       current
        DESCRIPTION  "Index of this table."
        ::= { asLinkAggrMtaEntry 1 }

    asLinkAggrMtaNEAddress OBJECT-TYPE
        SYNTAX       IpAddress
        MAX-ACCESS   not-accessible
        STATUS       current
        DESCRIPTION  "reserved"
        ::= { asLinkAggrMtaEntry 2 }

    asLinkAggrMtaModeMismatch OBJECT-TYPE
        SYNTAX       SeverityValue
        MAX-ACCESS   read-only
        STATUS       current
        DESCRIPTION  
            "Multi Traffic Aggregation Mode Mismatch Alarm.
            This alarm is asserted if the Multi Traffic Aggregation is
            configured when the H/W and/or F/W does not support the function.
            And also the alarm is asserted when the configuration is
            mismatched between local node and peer node."
        ::= { asLinkAggrMtaEntry 3 }

    asLinkAggrMtaVersion OBJECT-TYPE
        SYNTAX       Integer32
        MAX-ACCESS   read-only
        STATUS       current
        DESCRIPTION  
            "The support version of Multi Traffic Aggreation function."
        ::= { asLinkAggrMtaEntry 4 }

    asLinkAggrMtaEncapStatus OBJECT-TYPE
        SYNTAX       INTEGER { invalid(0), normal(1), fail(2) }
        MAX-ACCESS   read-only
        STATUS       current
        DESCRIPTION  
            "Multi Traffic Aggregation Encapsulation Status.
            When the Modem cannot build frames continuously, the object will
            assert the 'fail'.
            The value will change to 'normal' if the condition is cleared."
        ::= { asLinkAggrMtaEntry 5 }

    asLinkAggrMtaTCModeMismatch OBJECT-TYPE
        SYNTAX       SeverityValue
        MAX-ACCESS   read-only
        STATUS       current
        DESCRIPTION  
            "This object indicates the Transparent Clock Mode Mismatch Alarm
            for MTA Group."
        ::= { asLinkAggrMtaEntry 6 }

    asLinkAggrMtaTCCalibrationStatus OBJECT-TYPE
        SYNTAX       INTEGER { invalid(0), unlocked(1), locked(2) }
        MAX-ACCESS   read-only
        STATUS       current
        DESCRIPTION  
            "This object indicates the calibration status of Transparent
            Clock and Boundary Clock as logical interface(Multi Group). This
            object is valid only when Transparent Clock Mode and Boundary
            Clock is enabled and the Mode is correspond version."
        ::= { asLinkAggrMtaEntry 7 }

-----------------------------------------------
-- End User MIB Object Definitions
-----------------------------------------------

END
