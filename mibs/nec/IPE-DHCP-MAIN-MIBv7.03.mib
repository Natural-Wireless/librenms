--
-- ASN.1 MIB Definitions
-- Output Date: Fri Mar 05 09:45:11 2021
--

IPE-DHCP-MAIN-MIB DEFINITIONS ::= BEGIN

-----------------------------------------------
-- IMPORTS Definitions
-----------------------------------------------

    IMPORTS
        InterfaceIndex
            FROM IF-MIB
        enterprises, Integer32, IpAddress, NOTIFICATION-TYPE, OBJECT-TYPE
            FROM SNMPv2-SMI
        DateAndTime, MacAddress, RowStatus, TEXTUAL-CONVENTION
            FROM SNMPv2-TC;

-----------------------------------------------
-- Textual Convention Definitions
-----------------------------------------------

    EnableDisableValue ::= TEXTUAL-CONVENTION
        STATUS       current
        DESCRIPTION  "Enable/Disable Type"
        SYNTAX       INTEGER { invalid(0), disable(1), enable(2) }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    system5 OBJECT IDENTIFIER
        ::= { radioEquipment 5 }

-----------------------------------------------
-- system5 Group Definitions
-----------------------------------------------

    ipeConfigurationGroup OBJECT IDENTIFIER
        ::= { system5 3 }

    ipeCfgDhcpGroup OBJECT IDENTIFIER
        ::= { ipeConfigurationGroup 13 }

    ipeCfgDhcpMainServerTable OBJECT-TYPE
        SYNTAX       SEQUENCE OF IpeCfgDhcpMainServerEntry
        MAX-ACCESS   not-accessible
        STATUS       current
        DESCRIPTION  
            "IPv4 DHCP server/relay configuraion table for main traffic."
        ::= { ipeCfgDhcpGroup 2 }

    ipeCfgDhcpMainServerEntry OBJECT-TYPE
        SYNTAX       IpeCfgDhcpMainServerEntry
        MAX-ACCESS   not-accessible
        STATUS       current
        DESCRIPTION  "Entry of IPv4 DHCP server/relay configuraion table."
        INDEX        { ipeCfgDhcpMainServerIndex }
        ::= { ipeCfgDhcpMainServerTable 1 }

    IpeCfgDhcpMainServerEntry ::= SEQUENCE {
        ipeCfgDhcpMainServerIndex                  Integer32,
        ipeCfgDhcpMainServerNEAddress              IpAddress,
        ipeCfgDhcpMainServerEnable                 EnableDisableValue,
        ipeCfgDhcpMainServerMode                   INTEGER,
        ipeCfgDhcpMainServerInterface              InterfaceIndex,
        ipeCfgDhcpMainServerIpAddr                 IpAddress,
        ipeCfgDhcpMainServerLeaseTime              Integer32,
        ipeCfgDhcpMainServerLeaseAddrRangeBegin    IpAddress,
        ipeCfgDhcpMainServerLeaseAddrRangeEnd      IpAddress,
        ipeCfgDhcpMainServerLeaseAddrExcludeBegin  IpAddress,
        ipeCfgDhcpMainServerLeaseAddrExcludeEnd    IpAddress,
        ipeCfgDhcpMainServerOptGatewayAddrEnable   INTEGER,
        ipeCfgDhcpMainServerOptGatewayAddr         IpAddress,
        ipeCfgDhcpMainServerOptDnsServerPrimary    IpAddress,
        ipeCfgDhcpMainServerOptDnsServerSecondary  IpAddress,
        ipeCfgDhcpMainServerOptSpecifyEnable       EnableDisableValue,
        ipeCfgDhcpMainServerOptSpecifyId           Integer32,
        ipeCfgDhcpMainServerOptSpecifyType         INTEGER,
        ipeCfgDhcpMainServerOptSpecifyValue        OCTET STRING,
        ipeCfgDhcpMainServerSecurityLevel          INTEGER,
        ipeCfgDhcpMainServerRegisteredMacId        Integer32
    }

    ipeCfgDhcpMainServerIndex OBJECT-TYPE
        SYNTAX       Integer32 (1..16)
        MAX-ACCESS   not-accessible
        STATUS       current
        DESCRIPTION  "Index of this table."
        ::= { ipeCfgDhcpMainServerEntry 1 }

    ipeCfgDhcpMainServerNEAddress OBJECT-TYPE
        SYNTAX       IpAddress
        MAX-ACCESS   not-accessible
        STATUS       current
        DESCRIPTION  "Reserved object for northbound interface."
        ::= { ipeCfgDhcpMainServerEntry 2 }

    ipeCfgDhcpMainServerEnable OBJECT-TYPE
        SYNTAX       EnableDisableValue
        MAX-ACCESS   read-write
        STATUS       current
        DESCRIPTION  
            "Enable/Disable this DHCP server/relay agent.
            
            disable : DHCP server/relay agent is disabled
            enable  : DHCP server/relay agent is enabled"
        DEFVAL       { disable }
        ::= { ipeCfgDhcpMainServerEntry 3 }

    ipeCfgDhcpMainServerMode OBJECT-TYPE
        SYNTAX       INTEGER { invalid(0), server(1), relay(2) }
        MAX-ACCESS   read-write
        STATUS       current
        DESCRIPTION  
            "Configuration of operation mode.
            
            server : This instance is DHCP server mode.
            relay  : This instance is DHCP relay agent mode.
            
            When ipeCfgDhcpMainServerIndex is 1-3, both server and relay can
            configurable. In this case, the default value is server.
            When ipeCfgDhcpMainServerIndex is 4-16, only relay can
            configurable. In this case, the default value is relay."
        ::= { ipeCfgDhcpMainServerEntry 4 }

    ipeCfgDhcpMainServerInterface OBJECT-TYPE
        SYNTAX       InterfaceIndex
        MAX-ACCESS   read-write
        STATUS       current
        DESCRIPTION  
            "Interface index of local m-plane interface which communicate
            with DHCP client.
            The value of this object doesn't overlap with other instance."
        ::= { ipeCfgDhcpMainServerEntry 5 }

    ipeCfgDhcpMainServerIpAddr OBJECT-TYPE
        SYNTAX       IpAddress
        MAX-ACCESS   read-write
        STATUS       current
        DESCRIPTION  
            "IPv4 address of DHCP server. 
            This object is effective only if DHCP relay agent mode."
        ::= { ipeCfgDhcpMainServerEntry 6 }

    ipeCfgDhcpMainServerLeaseTime OBJECT-TYPE
        SYNTAX       Integer32 (0..0|60..259200)
        UNITS        "seconds"
        MAX-ACCESS   read-write
        STATUS       current
        DESCRIPTION  
            "The lease time of IPv4 Address provides to DHCP Client. The unit
            is seconds.
            0 means inifinity.
            This object is effective only if DHCP server mode."
        DEFVAL       { 86400 }
        ::= { ipeCfgDhcpMainServerEntry 7 }

    ipeCfgDhcpMainServerLeaseAddrRangeBegin OBJECT-TYPE
        SYNTAX       IpAddress
        MAX-ACCESS   read-write
        STATUS       current
        DESCRIPTION  
            "First IPv4 address within the range of lease address.
            This IP address is less equal than
            ipeCfgDhcpMainServerAddrRangeEnd.
            This object is effective only if DHCP server mode."
        DEFVAL       { '00000000'h }
        ::= { ipeCfgDhcpMainServerEntry 8 }

    ipeCfgDhcpMainServerLeaseAddrRangeEnd OBJECT-TYPE
        SYNTAX       IpAddress
        MAX-ACCESS   read-write
        STATUS       current
        DESCRIPTION  
            "Last IPv4 address within the range of lease address.
            This IPv4 address is greater equal than
            ipeCfgDhcpMainServerAddrRangeBegin. This object is effective only
            if DHCP server mode."
        DEFVAL       { '00000000'h }
        ::= { ipeCfgDhcpMainServerEntry 9 }

    ipeCfgDhcpMainServerLeaseAddrExcludeBegin OBJECT-TYPE
        SYNTAX       IpAddress
        MAX-ACCESS   read-write
        STATUS       current
        DESCRIPTION  
            "First IPv4 address within the range of lease exclude address.
            DHCP server don't lease IP address within lease exclude address.
            This IPv4 address is less equal than ipeCfgDhcpMainServerAddr-
            ExcludeEnd.
            This object is effective only if  DHCP server mode."
        DEFVAL       { '00000000'h }
        ::= { ipeCfgDhcpMainServerEntry 10 }

    ipeCfgDhcpMainServerLeaseAddrExcludeEnd OBJECT-TYPE
        SYNTAX       IpAddress
        MAX-ACCESS   read-write
        STATUS       current
        DESCRIPTION  
            "Last IPv4 address within the range of lease exclude address.
            DHCP server don't lease IP address within lease exclude address.
            This IPv4 address is less equal than ipeCfgDhcpMainServerAddr-
            ExcludeBegin.
            This object is effective only if  DHCP server mode."
        DEFVAL       { '00000000'h }
        ::= { ipeCfgDhcpMainServerEntry 11 }

    ipeCfgDhcpMainServerOptGatewayAddrEnable OBJECT-TYPE
        SYNTAX       INTEGER {
                         invalid(0),
                         enabledInterface(1),
                         enabledSpecify(2),
                         disabled(3)
                     }
        MAX-ACCESS   read-write
        STATUS       current
        DESCRIPTION  
            "Switch that how to handle gateway IP address option on DHCP
            server.
            
              enabledInterface : Use interface IP address. DHCP server
                                 provides gateway IP address configured on 
                                 interface which is set to 
                                 ipeCfgDhcpMainServerInterface.
              enabledSpecify   : Use IP address which is set to
                                 ipeCfgDhcpMainServerOptGatewayAddr.
              disabled         : DHCP server doesn't provide gateway IP 
                                 address.
            
            This object is effective only if DHCP server mode."
        DEFVAL       { enabledInterface }
        ::= { ipeCfgDhcpMainServerEntry 12 }

    ipeCfgDhcpMainServerOptGatewayAddr OBJECT-TYPE
        SYNTAX       IpAddress
        MAX-ACCESS   read-write
        STATUS       current
        DESCRIPTION  
            "Gateway IP address which is provided by DHCP server.
            
            This object is effective only if DHCP server mode and
            ipeCfgDhcpMainServerOptGatewayAddrEnable is set to
            enabledSpecify."
        DEFVAL       { '00000000'h }
        ::= { ipeCfgDhcpMainServerEntry 13 }

    ipeCfgDhcpMainServerOptDnsServerPrimary OBJECT-TYPE
        SYNTAX       IpAddress
        MAX-ACCESS   read-write
        STATUS       current
        DESCRIPTION  
            "Primary DNS server address which is provided by DHCP server.
            
            This object is effective only if DHCP server mode."
        DEFVAL       { '00000000'h }
        ::= { ipeCfgDhcpMainServerEntry 14 }

    ipeCfgDhcpMainServerOptDnsServerSecondary OBJECT-TYPE
        SYNTAX       IpAddress
        MAX-ACCESS   read-write
        STATUS       current
        DESCRIPTION  
            "Secoundary DNS server address which is provided by DHCP server.
            
            In order to configure this object.
            ipeCfgDhcpMainServerOptDnsServerPrimary must be set in advance.
            
            
            This object is effective only if DHCP server mode."
        DEFVAL       { '00000000'h }
        ::= { ipeCfgDhcpMainServerEntry 15 }

    ipeCfgDhcpMainServerOptSpecifyEnable OBJECT-TYPE
        SYNTAX       EnableDisableValue
        MAX-ACCESS   read-write
        STATUS       current
        DESCRIPTION  
            "Switch that whether DHCP server add user specified option to
            DHCP message.
            
            enable  : DHCP server add user specified option.
            disable : DHCP server doesn't add user specified otption.
            
            This object is effective only if DHCP server mode."
        DEFVAL       { disable }
        ::= { ipeCfgDhcpMainServerEntry 16 }

    ipeCfgDhcpMainServerOptSpecifyId OBJECT-TYPE
        SYNTAX       Integer32 (0..255)
        MAX-ACCESS   read-write
        STATUS       current
        DESCRIPTION  
            "Option id which DHCP server adds user specified option to DHCP
            message.
            This object is effective only if DHCP server mode and ipeCfgDhcp-
            MainServerOptSpecifyEnable is set to enabled."
        DEFVAL       { 0 }
        ::= { ipeCfgDhcpMainServerEntry 17 }

    ipeCfgDhcpMainServerOptSpecifyType OBJECT-TYPE
        SYNTAX       INTEGER {
                         invalid(0),
                         ipv4(1),
                         ipv6(2),
                         displayString(3),
                         octetString(4)
                     }
        MAX-ACCESS   read-write
        STATUS       current
        DESCRIPTION  
            "Option type which DHCP server adds to DHCP message.
            This object is effective only if DHCP server mode and ipeCfgDhcp-
            MainServerOptSpecifyEnable is set to enabled."
        DEFVAL       { ipv4 }
        ::= { ipeCfgDhcpMainServerEntry 18 }

    ipeCfgDhcpMainServerOptSpecifyValue OBJECT-TYPE
        SYNTAX       OCTET STRING (SIZE(0..255))
        MAX-ACCESS   read-write
        STATUS       current
        DESCRIPTION  
            "Option value which DHCP server adds to DHCP message.
            This object is decoded according to
            ipeCfgDhcpMainServerOptSpecifyType.
            
            ipv4          : Syntax is IpAddress.
            ipv6          : Syntax is Ipv6Address.
            displayString : Syntax is DisplayString.
            octetString   : Syntax is OCTET STRING.
            
            This object is effective only if DHCP server mode and
            ipeCfgDhcpMainServerOptSpecifyEnable is set to enabled."
        ::= { ipeCfgDhcpMainServerEntry 19 }

    ipeCfgDhcpMainServerSecurityLevel OBJECT-TYPE
        SYNTAX       INTEGER { invalid(0), any(1), onlyRegistered(2) }
        MAX-ACCESS   read-write
        STATUS       current
        DESCRIPTION  
            "Security level of this DHCP server.
            
            any            : DHCP server doesn't check MAC address except for
                             rejected MAC address.
            onlyRegistered : DHCP server provides IP address only to
                             registered MAC addresss.
            
            Note : Rejected MAC address is examined even if
                   ipeCfgDhcpMainServerSecurityLevel is set to any.
            This object is effective only if DHCP server mode."
        DEFVAL       { any }
        ::= { ipeCfgDhcpMainServerEntry 20 }

    ipeCfgDhcpMainServerRegisteredMacId OBJECT-TYPE
        SYNTAX       Integer32 (0..3)
        MAX-ACCESS   read-write
        STATUS       current
        DESCRIPTION  
            "The identifier of ipeCfgDhcpMainServerRegisteredMacEnrty. 
            0 means no registered/rejected IP address exists.
            This object is effective only if DHCP server mode."
        DEFVAL       { 0 }
        ::= { ipeCfgDhcpMainServerEntry 21 }

    ipeCfgDhcpMainRegisteredMacTable OBJECT-TYPE
        SYNTAX       SEQUENCE OF IpeCfgDhcpMainRegisteredMacEntry
        MAX-ACCESS   not-accessible
        STATUS       current
        DESCRIPTION  "IPv4 registered MAC address table for DHCP server."
        ::= { ipeCfgDhcpGroup 3 }

    ipeCfgDhcpMainRegisteredMacEntry OBJECT-TYPE
        SYNTAX       IpeCfgDhcpMainRegisteredMacEntry
        MAX-ACCESS   not-accessible
        STATUS       current
        DESCRIPTION  "Entry of IPv4 registered MAC address table."
        INDEX        {
                         ipeCfgDhcpMainRegisteredMacId,
                         ipeCfgDhcpMainRegisteredMacNo
                     }
        ::= { ipeCfgDhcpMainRegisteredMacTable 1 }

    IpeCfgDhcpMainRegisteredMacEntry ::= SEQUENCE {
        ipeCfgDhcpMainRegisteredMacId         Integer32,
        ipeCfgDhcpMainRegisteredMacNo         Integer32,
        ipeCfgDhcpMainRegisteredMacNEAddress  IpAddress,
        ipeCfgDhcpMainRegisteredMacAddr       MacAddress,
        ipeCfgDhcpMainRegisteredMacIpAddr     IpAddress,
        ipeCfgDhcpMainRegisteredMacRowStatus  RowStatus
    }

    ipeCfgDhcpMainRegisteredMacId OBJECT-TYPE
        SYNTAX       Integer32 (1..3)
        MAX-ACCESS   not-accessible
        STATUS       current
        DESCRIPTION  
            "Index of this table. This object means identifier of registered
            MAC entry."
        ::= { ipeCfgDhcpMainRegisteredMacEntry 1 }

    ipeCfgDhcpMainRegisteredMacNo OBJECT-TYPE
        SYNTAX       Integer32 (1..256)
        MAX-ACCESS   not-accessible
        STATUS       current
        DESCRIPTION  
            "Index of this table. This object means MAC address number whthin
            this registered MAC entry."
        ::= { ipeCfgDhcpMainRegisteredMacEntry 2 }

    ipeCfgDhcpMainRegisteredMacNEAddress OBJECT-TYPE
        SYNTAX       IpAddress
        MAX-ACCESS   not-accessible
        STATUS       current
        DESCRIPTION  "Reserved object for northbound interface."
        ::= { ipeCfgDhcpMainRegisteredMacEntry 3 }

    ipeCfgDhcpMainRegisteredMacAddr OBJECT-TYPE
        SYNTAX       MacAddress
        MAX-ACCESS   read-create
        STATUS       current
        DESCRIPTION  
            "This object means registered MAC address. When ipeCfgDhcpMain-
            ServerSecurityLevel is set to onlyRegisterd, DHCP server accept
            DHCP message sent from registered MAC address.
            
            This object must be set when the row is created."
        ::= { ipeCfgDhcpMainRegisteredMacEntry 4 }

    ipeCfgDhcpMainRegisteredMacIpAddr OBJECT-TYPE
        SYNTAX       IpAddress
        MAX-ACCESS   read-create
        STATUS       current
        DESCRIPTION  
            "IP address correspond to registered MAC address. If DHCP server
            receives DHCP DISCOVER from registered MAC address, it provide 
            corresponding IP address set to this object. 
            
            When this object is set to 0.0.0.0, DHCP server provide any 
            address whthin the lease address range.
            When this object is set to 255.255.255.255, DHCP server treats
            this MAC address as rejected MAC Address."
        DEFVAL       { '00000000'h }
        ::= { ipeCfgDhcpMainRegisteredMacEntry 5 }

    ipeCfgDhcpMainRegisteredMacRowStatus OBJECT-TYPE
        SYNTAX       RowStatus
        MAX-ACCESS   read-create
        STATUS       current
        DESCRIPTION  
            "RowStatus of this entry. The system supports three values shonw
            below.
            
            active(1)      : change attribute in existing instance.
            createAndGo(4) : create the instance.
            destroy(6)     : delete the instance."
        ::= { ipeCfgDhcpMainRegisteredMacEntry 6 }

    ipeCommandGroup OBJECT IDENTIFIER
        ::= { system5 8 }

    ipeCmdDhcpGroup OBJECT IDENTIFIER
        ::= { ipeCommandGroup 13 }

    ipeCmdDhcpMainTable OBJECT-TYPE
        SYNTAX       SEQUENCE OF IpeCmdDhcpMainEntry
        MAX-ACCESS   not-accessible
        STATUS       current
        DESCRIPTION  "Maintenance table for DHCP server."
        ::= { ipeCmdDhcpGroup 1 }

    ipeCmdDhcpMainEntry OBJECT-TYPE
        SYNTAX       IpeCmdDhcpMainEntry
        MAX-ACCESS   not-accessible
        STATUS       current
        DESCRIPTION  "Command entry for IPv4 DHCP server."
        INDEX        { ipeCmdDhcpMainIndex, ipeCmdDhcpMainLeaseIpAddr }
        ::= { ipeCmdDhcpMainTable 1 }

    IpeCmdDhcpMainEntry ::= SEQUENCE {
        ipeCmdDhcpMainIndex         Integer32,
        ipeCmdDhcpMainLeaseIpAddr   IpAddress,
        ipeCmdDhcpMainNEAddress     IpAddress,
        ipeCmdDhcpMainManualDelete  INTEGER
    }

    ipeCmdDhcpMainIndex OBJECT-TYPE
        SYNTAX       Integer32 (1..3)
        MAX-ACCESS   not-accessible
        STATUS       current
        DESCRIPTION  "Index of table."
        ::= { ipeCmdDhcpMainEntry 1 }

    ipeCmdDhcpMainLeaseIpAddr OBJECT-TYPE
        SYNTAX       IpAddress
        MAX-ACCESS   not-accessible
        STATUS       current
        DESCRIPTION  "The lease IP Address."
        ::= { ipeCmdDhcpMainEntry 2 }

    ipeCmdDhcpMainNEAddress OBJECT-TYPE
        SYNTAX       IpAddress
        MAX-ACCESS   not-accessible
        STATUS       current
        DESCRIPTION  "Index of table."
        ::= { ipeCmdDhcpMainEntry 3 }

    ipeCmdDhcpMainManualDelete OBJECT-TYPE
        SYNTAX       INTEGER { invalid(0), normal(1), manualDelete(2) }
        MAX-ACCESS   read-write
        STATUS       current
        DESCRIPTION  
            "Operator manually deletes this lease address.
            
            normal       : can not set this value. 
            manualDelete : Delete this lease address. 
                           If ipeCmdDhcpMainLeaseIpAddr is set to 0.0.0.0, 
                           DHCP server deletes all entry in corresponding
                           ipeStsDhcpMainLeaseAddrEntry.
            
            Note : When you read this object, the system alwasys return
            normal."
        ::= { ipeCmdDhcpMainEntry 4 }

-----------------------------------------------
-- End User MIB Object Definitions
-----------------------------------------------

END
